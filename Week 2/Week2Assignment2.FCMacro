# -*- coding: utf-8 -*-

# Macro Begin: /Users/anish/ProBUILD_FreeCAD/Week2Sketch2.FCMacro +++++++++++++++++++++++++++++++++++++++++++++++++
import FreeCAD
import PartDesign
import PartDesignGui
import Spreadsheet
import Sketcher

# Gui.runCommand('Std_DlgMacroRecord',0)
### Begin command Std_New
App.newDocument()
# App.setActiveDocument("Unnamed")
# App.ActiveDocument=App.getDocument("Unnamed")
# Gui.ActiveDocument=Gui.getDocument("Unnamed")
# Gui.activeDocument().activeView().viewDefaultOrientation()
### End command Std_New
### Begin command PartDesign_Body
App.activeDocument().addObject('PartDesign::Body','Body')
App.ActiveDocument.getObject('Body').Label = 'Body'
# Gui.activateView('Gui::View3DInventor', True)
# Gui.activeView().setActiveObject('pdbody', App.activeDocument().Body)
# Gui.Selection.clearSelection()
# Gui.Selection.addSelection(App.ActiveDocument.Body)
App.ActiveDocument.recompute()
### End command PartDesign_Body
# Gui.Selection.addSelection('Unnamed','Body')
# Gui.runCommand('PartDesign_CompSketches',0)
# Gui.Selection.clearSelection()
# Gui.Selection.addSelection('Unnamed','Body','Origin.XY_Plane.')
App.getDocument('Unnamed').getObject('Body').newObject('Sketcher::SketchObject','Sketch')
App.getDocument('Unnamed').getObject('Sketch').AttachmentSupport = (App.getDocument('Unnamed').getObject('XY_Plane'),[''])
App.getDocument('Unnamed').getObject('Sketch').MapMode = 'FlatFace'
App.ActiveDocument.recompute()
# Gui.getDocument('Unnamed').setEdit(App.getDocument('Unnamed').getObject('Body'), 0, 'Sketch.')
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
### Begin command Std_Workbench
# Gui.activateWorkbench("SpreadsheetWorkbench")
### End command Std_Workbench
### Begin command Spreadsheet_CreateSheet
App.activeDocument().addObject('Spreadsheet::Sheet','Spreadsheet')
# Gui.Selection.clearSelection()
# 
# Gui.Selection.addSelection(App.activeDocument().Name,'Spreadsheet')
### End command Spreadsheet_CreateSheet
# Gui.Selection.addSelection('Unnamed','Spreadsheet')
# App.getDocument('Unnamed').getObject('Spreadsheet').ViewObject.doubleClicked()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
# Gui.Selection.clearSelection()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.ActiveDocument.recompute()
App.getDocument('Unnamed').getObject('Spreadsheet').setAlias('B1', 'gear_inner_rad')
App.getDocument('Unnamed').recompute()
App.getDocument('Unnamed').getObject('Spreadsheet').setAlias('B2', 'gear_outer_rad')
App.getDocument('Unnamed').recompute()
App.getDocument('Unnamed').getObject('Spreadsheet').setAlias('B3', 'gear_tooth_rad')
App.getDocument('Unnamed').recompute()
App.getDocument('Unnamed').getObject('Spreadsheet').setAlias('B4', 'fillet_rad')
App.getDocument('Unnamed').recompute()
App.getDocument('Unnamed').getObject('Spreadsheet').setAlias('B5', 'botright_step_ydist')
App.getDocument('Unnamed').recompute()
App.getDocument('Unnamed').getObject('Spreadsheet').setAlias('B6', 'midstep_ydist')
App.getDocument('Unnamed').recompute()
App.getDocument('Unnamed').getObject('Spreadsheet').setAlias('B7', 'left_portr_ydist')
App.getDocument('Unnamed').recompute()
App.getDocument('Unnamed').getObject('Spreadsheet').setAlias('B8', 'portr_xdist')
App.getDocument('Unnamed').recompute()
App.getDocument('Unnamed').getObject('Spreadsheet').setAlias('B9', 'portr_edge_xdist')
App.getDocument('Unnamed').recompute()
App.getDocument('Unnamed').getObject('Spreadsheet').setAlias('B10', 'botleft_xdist')
App.getDocument('Unnamed').recompute()
App.getDocument('Unnamed').getObject('Spreadsheet').setAlias('B11', 'botmid_xdist')
App.getDocument('Unnamed').recompute()
App.getDocument('Unnamed').getObject('Spreadsheet').setAlias('B12', 'topright_xdist')
App.getDocument('Unnamed').recompute()
App.getDocument('Unnamed').getObject('Spreadsheet').setAlias('B13', 'topmid_xdist')
App.getDocument('Unnamed').recompute()
App.getDocument('Unnamed').getObject('Spreadsheet').setAlias('B14', 'edgecut_ydist')
App.getDocument('Unnamed').recompute()
App.getDocument('Unnamed').getObject('Spreadsheet').setAlias('B15', 'edgecut_xdist')
App.getDocument('Unnamed').recompute()
App.getDocument('Unnamed').getObject('Spreadsheet').setAlias('B16', 'height')
App.getDocument('Unnamed').recompute()
App.getDocument('Unnamed').getObject('Spreadsheet').setAlias('B17', 'slant_len')
App.getDocument('Unnamed').recompute()
App.getDocument('Unnamed').getObject('Spreadsheet').setAlias('B18', 'inner_dip_len')
App.getDocument('Unnamed').recompute()
App.getDocument('Unnamed').getObject('Spreadsheet').setAlias('B19', 'dip_length')
App.getDocument('Unnamed').recompute()
App.getDocument('Unnamed').getObject('Spreadsheet').setAlias('B20', 'inner_dip_depth')
App.getDocument('Unnamed').recompute()
# Gui.Selection.addSelection('Unnamed','Body','Sketch.')
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CreatePolyline',0)
# Gui.Selection.addSelection('Unnamed','Body','Sketch.V_Axis',0,28.2219,0.002,False)
# Gui.runCommand('Sketcher_CompCreateRectangles',0)
# Gui.Selection.clearSelection()
ActiveSketch = App.getDocument('Unnamed').getObject('Sketch')

lastGeoId = len(ActiveSketch.Geometry)

geoList = []
geoList.append(Part.LineSegment(App.Vector(25.064798, 130.987793, 0.000000),App.Vector(25.064798, 12.998293, 0.000000)))
geoList.append(Part.LineSegment(App.Vector(25.064798, 12.998293, 0.000000),App.Vector(83.744057, 12.998293, 0.000000)))
geoList.append(Part.LineSegment(App.Vector(83.744057, 12.998293, 0.000000),App.Vector(83.744057, 130.987793, 0.000000)))
geoList.append(Part.LineSegment(App.Vector(83.744057, 130.987793, 0.000000),App.Vector(25.064798, 130.987793, 0.000000)))
App.getDocument('Unnamed').getObject('Sketch').addGeometry(geoList,False)
del geoList

constraintList = []
constraintList.append(Sketcher.Constraint('Coincident', 0, 2, 1, 1))
constraintList.append(Sketcher.Constraint('Coincident', 1, 2, 2, 1))
constraintList.append(Sketcher.Constraint('Coincident', 2, 2, 3, 1))
constraintList.append(Sketcher.Constraint('Coincident', 3, 2, 0, 1))
constraintList.append(Sketcher.Constraint('Vertical', 0))
constraintList.append(Sketcher.Constraint('Vertical', 2))
constraintList.append(Sketcher.Constraint('Horizontal', 1))
constraintList.append(Sketcher.Constraint('Horizontal', 3))
App.getDocument('Unnamed').getObject('Sketch').addConstraint(constraintList)
del constraintList

constraintList = []
# Gui.runCommand('Sketcher_CompDimensionTools',0)
App.getDocument('Unnamed').getObject('Sketch').addConstraint(Sketcher.Constraint('Distance',0,1,0,2,117.989500)) 
# Gui.Selection.addSelection('Unnamed','Body','Sketch.Edge1',25.0648,80.7029,0)
App.getDocument('Unnamed').getObject('Sketch').addConstraint(Sketcher.Constraint('DistanceY',0,2,0,1,117.989500)) 
App.getDocument('Unnamed').Sketch.setExpression('Constraints[8]', u'<<Spreadsheet>>.height')
# Gui.Selection.clearSelection()
App.getDocument('Unnamed').getObject('Sketch').addConstraint(Sketcher.Constraint('Distance',1,1,1,2,58.679259)) 
# Gui.Selection.addSelection('Unnamed','Body','Sketch.Edge2',60.3473,23.1867,0)
App.getDocument('Unnamed').getObject('Sketch').addConstraint(Sketcher.Constraint('DistanceX',1,1,1,2,58.679259)) 
# Gui.Selection.clearSelection()
# Gui.runCommand('Sketcher_CreateFillet',0)
# Gui.runCommand('Sketcher_CompCreateFillets',0)
# Gui.Selection.addSelection('Unnamed','Body','Sketch.Edge4',34.2721,98.1867,0)
App.getDocument('Unnamed').getObject('Sketch').fillet(3,0,App.Vector(34.272144,98.186693,0),App.Vector(25.064798,91.934807,0),6.915260,True,True,False)
# Gui.Selection.clearSelection()
# Gui.Selection.addSelection('Unnamed','Body','Sketch.Edge2',71.2731,23.1867,0)
App.getDocument('Unnamed').getObject('Sketch').fillet(1,2,App.Vector(71.273064,23.186693,0),App.Vector(83.744057,28.172239,0),8.993753,True,True,False)
# Gui.Selection.clearSelection()
# Gui.Selection.addSelection('Unnamed','Body','Sketch.Edge5',26.0278,94.7916,0.008,False)
# Gui.Selection.addSelection('Unnamed','Body','Sketch.Edge7',80.0367,24.9043,0.008,False)
### Begin command Sketcher_ConstrainEqual
App.getDocument('Unnamed').getObject('Sketch').addConstraint(Sketcher.Constraint('Equal',4,6))
### End command Sketcher_ConstrainEqual
# Gui.Selection.clearSelection()
# Gui.runCommand('Sketcher_CompDimensionTools',0)
App.getDocument('Unnamed').getObject('Sketch').addConstraint(Sketcher.Constraint('Radius',4,8.173670)) 
# Gui.Selection.addSelection('Unnamed','Body','Sketch.Edge5',25.7197,95.5489,0)
App.getDocument('Unnamed').Sketch.setExpression('Constraints[16]', u'<<Spreadsheet>>.fillet_rad')
# Gui.Selection.clearSelection()
# Gui.Selection.addSelection('Unnamed','Body','Sketch.Vertex2',26.6883,21.7592,0.014,False)
# Gui.Selection.addSelection('Unnamed','Body','Sketch.RootPoint',0,0,0.01,False)
### Begin command Sketcher_ConstrainCoincidentUnified
App.getDocument('Unnamed').getObject('Sketch').addConstraint(Sketcher.Constraint('Coincident',0,2,-1,1))
### End command Sketcher_ConstrainCoincidentUnified
# Gui.Selection.clearSelection()
App.getDocument('Unnamed').getObject('Sketch').movePoint(3,0,App.Vector(0.779949,4.647949,0),1)
App.getDocument('Unnamed').getObject('Sketch').movePoint(2,0,App.Vector(-17.160910,-0.311981,0),1)
# Gui.runCommand('Sketcher_CreateLine',0)
# Gui.runCommand('Sketcher_CreatePolyline',0)
# Gui.runCommand('Sketcher_CreatePolyline',0)
# Gui.runCommand('Sketcher_CreatePolyline',0)
# Gui.runCommand('Sketcher_CreatePolyline',0)
App.getDocument('Unnamed').getObject('Sketch').addGeometry(Part.LineSegment(App.Vector(52.740643,0.000000,0),App.Vector(52.740643,10.163851,0)),False)
App.getDocument('Unnamed').getObject('Sketch').addConstraint(Sketcher.Constraint('PointOnObject',8,1,1)) 
App.getDocument('Unnamed').getObject('Sketch').addConstraint(Sketcher.Constraint('Vertical',8)) 
App.getDocument('Unnamed').getObject('Sketch').addGeometry(Part.LineSegment(App.Vector(52.740643,10.163851,0),App.Vector(27.708702,10.036136,0)),False)
App.getDocument('Unnamed').getObject('Sketch').addConstraint(Sketcher.Constraint('Coincident',8,2,9,1)) 
App.getDocument('Unnamed').getObject('Sketch').addConstraint(Sketcher.Constraint('Horizontal',9)) 
App.getDocument('Unnamed').getObject('Sketch').addGeometry(Part.LineSegment(App.Vector(27.708702,10.163851,0),App.Vector(27.580986,35.578938,0)),False)
App.getDocument('Unnamed').getObject('Sketch').addConstraint(Sketcher.Constraint('Coincident',9,2,10,1)) 
App.getDocument('Unnamed').getObject('Sketch').addConstraint(Sketcher.Constraint('Vertical',10)) 
App.getDocument('Unnamed').getObject('Sketch').addGeometry(Part.LineSegment(App.Vector(27.708702,35.578938,0),App.Vector(24.643562,35.578938,0)),False)
App.getDocument('Unnamed').getObject('Sketch').addConstraint(Sketcher.Constraint('Coincident',10,2,11,1)) 
App.getDocument('Unnamed').getObject('Sketch').addConstraint(Sketcher.Constraint('Horizontal',11)) 
App.getDocument('Unnamed').getObject('Sketch').addGeometry(Part.LineSegment(App.Vector(24.643562,35.578938,0),App.Vector(24.643562,21.147255,0)),False)
App.getDocument('Unnamed').getObject('Sketch').addConstraint(Sketcher.Constraint('Coincident',11,2,12,1)) 
App.getDocument('Unnamed').getObject('Sketch').addConstraint(Sketcher.Constraint('Vertical',12)) 
App.getDocument('Unnamed').getObject('Sketch').addGeometry(Part.LineSegment(App.Vector(24.643562,21.147255,0),App.Vector(21.961573,21.019541,0)),False)
App.getDocument('Unnamed').getObject('Sketch').addConstraint(Sketcher.Constraint('Coincident',12,2,13,1)) 
App.getDocument('Unnamed').getObject('Sketch').addGeometry(Part.LineSegment(App.Vector(21.961573,21.019541,0),App.Vector(21.833858,26.128099,0)),False)
App.getDocument('Unnamed').getObject('Sketch').addConstraint(Sketcher.Constraint('Coincident',13,2,14,1)) 
App.getDocument('Unnamed').getObject('Sketch').addConstraint(Sketcher.Constraint('Vertical',14)) 
App.getDocument('Unnamed').getObject('Sketch').addGeometry(Part.LineSegment(App.Vector(21.961573,26.128099,0),App.Vector(19.407288,25.872673,0)),False)
App.getDocument('Unnamed').getObject('Sketch').addConstraint(Sketcher.Constraint('Coincident',14,2,15,1)) 
App.getDocument('Unnamed').getObject('Sketch').addGeometry(Part.LineSegment(App.Vector(19.407288,25.872673,0),App.Vector(19.535004,20.891829,0)),False)
App.getDocument('Unnamed').getObject('Sketch').addConstraint(Sketcher.Constraint('Coincident',15,2,16,1)) 
App.getDocument('Unnamed').getObject('Sketch').addConstraint(Sketcher.Constraint('Vertical',16)) 
App.getDocument('Unnamed').getObject('Sketch').addGeometry(Part.LineSegment(App.Vector(19.407288,20.891829,0),App.Vector(15.448154,20.891829,0)),False)
App.getDocument('Unnamed').getObject('Sketch').addConstraint(Sketcher.Constraint('Coincident',16,2,17,1)) 
App.getDocument('Unnamed').getObject('Sketch').addConstraint(Sketcher.Constraint('Horizontal',17)) 
App.getDocument('Unnamed').getObject('Sketch').addGeometry(Part.LineSegment(App.Vector(15.448154,20.891829,0),App.Vector(15.448154,35.195797,0)),False)
App.getDocument('Unnamed').getObject('Sketch').addConstraint(Sketcher.Constraint('Coincident',17,2,18,1)) 
App.getDocument('Unnamed').getObject('Sketch').addConstraint(Sketcher.Constraint('Vertical',18)) 
App.getDocument('Unnamed').getObject('Sketch').addGeometry(Part.LineSegment(App.Vector(15.448154,35.195797,0),App.Vector(0.000000,35.000000,0)),False)
App.getDocument('Unnamed').getObject('Sketch').addConstraint(Sketcher.Constraint('Coincident',18,2,19,1)) 
App.getDocument('Unnamed').getObject('Sketch').addConstraint(Sketcher.Constraint('Symmetric',0,1,0,2,19,2)) 
App.getDocument('Unnamed').getObject('Sketch').addConstraint(Sketcher.Constraint('Horizontal',19)) 
# Gui.Selection.addSelection('Unnamed','Body','Sketch.Edge16',20.8137,26.0133,0.008,False)
# Gui.Selection.addSelection('Unnamed','Body','Sketch.Edge14',23.5619,21.0957,0.008,False)
### Begin command Sketcher_ConstrainHorizontal
App.getDocument('Unnamed').getObject('Sketch').addConstraint(Sketcher.Constraint('Horizontal',15))
App.getDocument('Unnamed').getObject('Sketch').addConstraint(Sketcher.Constraint('Horizontal',13))
### End command Sketcher_ConstrainHorizontal
# Gui.Selection.clearSelection()
# Gui.runCommand('Sketcher_CompDimensionTools',0)
App.getDocument('Unnamed').getObject('Sketch').addConstraint(Sketcher.Constraint('Distance',8,1,8,2,10.163851)) 
# Gui.Selection.addSelection('Unnamed','Body','Sketch.Edge9',52.7406,5.83069,0)
App.getDocument('Unnamed').getObject('Sketch').addConstraint(Sketcher.Constraint('DistanceY',8,1,8,2,10.163851)) 
App.getDocument('Unnamed').getObject('Sketch').addConstraint(Sketcher.Constraint('Distance',2,1,8,10.679729)) 
# Gui.Selection.addSelection('Unnamed','Body','Sketch.Edge3',63.4204,9.25506,0)
App.getDocument('Unnamed').Sketch.setExpression('Constraints[43]', u'<<Spreadsheet>>.botright_step_ydist')
# Gui.Selection.clearSelection()
# Gui.runCommand('Std_Undo',0)
App.getDocument('Unnamed').getObject('Sketch').addConstraint(Sketcher.Constraint('Distance',8,1,8,2,10.163851)) 
# Gui.Selection.addSelection('Unnamed','Body','Sketch.Edge9',52.7406,5.08193,0)
App.getDocument('Unnamed').getObject('Sketch').addConstraint(Sketcher.Constraint('DistanceY',8,1,8,2,10.163851)) 
App.getDocument('Unnamed').getObject('Sketch').addConstraint(Sketcher.Constraint('Distance',2,1,8,10.679729)) 
# Gui.Selection.addSelection('Unnamed','Body','Sketch.Edge3',63.4204,7.02922,0)
App.getDocument('Unnamed').Sketch.setExpression('Constraints[43]', u'<<Spreadsheet>>.botleft_xdist')
# Gui.Selection.clearSelection()
App.getDocument('Unnamed').getObject('Sketch').addConstraint(Sketcher.Constraint('Distance',8,1,8,2,10.163851)) 
# Gui.Selection.addSelection('Unnamed','Body','Sketch.Edge9',46.901,4.17771,0)
App.getDocument('Unnamed').getObject('Sketch').addConstraint(Sketcher.Constraint('DistanceY',8,1,8,2,10.163851)) 
App.getDocument('Unnamed').Sketch.setExpression('Constraints[44]', u'<<Spreadsheet>>.botright_step_ydist')
# Gui.Selection.clearSelection()
App.getDocument('Unnamed').getObject('Sketch').addConstraint(Sketcher.Constraint('Distance',9,1,9,2,19.192277)) 
# Gui.Selection.addSelection('Unnamed','Body','Sketch.Edge10',37.3048,15,0)
App.getDocument('Unnamed').getObject('Sketch').addConstraint(Sketcher.Constraint('DistanceX',9,2,9,1,19.192277)) 
App.getDocument('Unnamed').Sketch.setExpression('Constraints[45]', u'<<Spreadsheet>>.botmid_xdist')
# Gui.Selection.clearSelection()
App.getDocument('Unnamed').getObject('Sketch').addConstraint(Sketcher.Constraint('Distance',10,1,10,2,20.578938)) 
# Gui.Selection.addSelection('Unnamed','Body','Sketch.Edge11',26.9327,20.9737,0)
App.getDocument('Unnamed').getObject('Sketch').addConstraint(Sketcher.Constraint('DistanceY',10,1,10,2,20.578938)) 
App.getDocument('Unnamed').getObject('Sketch').addConstraint(Sketcher.Constraint('Distance',0,1,10,26.932690)) 
# Gui.Selection.addSelection('Unnamed','Body','Sketch.Edge1',0,22.1232,0)
App.getDocument('Unnamed').Sketch.setExpression('Constraints[46]', u'<<Spreadsheet>>.botmid_xdist')
# Gui.Selection.clearSelection()
App.getDocument('Unnamed').getObject('Sketch').movePoint(18,2,App.Vector(8.199423,35.568996,0),0)
App.getDocument('Unnamed').getObject('Sketch').movePoint(11,2,App.Vector(18.572895,35.288631,0),0)
App.getDocument('Unnamed').getObject('Sketch').movePoint(11,2,App.Vector(22.708267,34.587723,0),0)
App.getDocument('Unnamed').getObject('Sketch').movePoint(16,2,App.Vector(12.124521,21.270426,0),0)
App.getDocument('Unnamed').getObject('Sketch').movePoint(13,2,App.Vector(15.208527,21.340519,0),0)
App.getDocument('Unnamed').getObject('Sketch').movePoint(12,2,App.Vector(18.082258,21.690973,0),0)
# Gui.Selection.addSelection('Unnamed','Body','Sketch.Edge12',19.7694,34.5877,0.008,False)
# Gui.Selection.addSelection('Unnamed','Body','Sketch.Edge20',4.44368,35,0.008,False)
# Gui.runCommand('Sketcher_ConstrainHorizontal',0)
# Gui.Selection.clearSelection()
# Gui.runCommand('Std_Undo',0)
App.getDocument('Unnamed').getObject('Sketch').movePoint(11,2,App.Vector(17.748362,33.914246,0),0)
# Gui.Selection.addSelection('Unnamed','Body','Sketch.Edge11',21,27.9888,0.008,False)
### Begin command Sketcher_CompDimensionTools
App.getDocument('Unnamed').getObject('Sketch').addConstraint(Sketcher.Constraint('Distance',10,1,10,2,18.914246)) 
### End command Sketcher_CompDimensionTools
# Gui.Selection.clearSelection()
App.getDocument('Unnamed').getObject('Sketch').addConstraint(Sketcher.Constraint('DistanceY',10,1,10,2,18.914246)) 
App.getDocument('Unnamed').Sketch.setExpression('Constraints[47]', u'<<Spreadsheet>>.midstep_ydist')
# Gui.Selection.addSelection('Unnamed','Body','Sketch.Vertex38',8.19942,35,0.014,False)
# Gui.Selection.addSelection('Unnamed','Body','Sketch.Vertex24',17.7484,37,0.014,False)
### Begin command Sketcher_ConstrainHorizontal
App.getDocument('Unnamed').getObject('Sketch').addConstraint(Sketcher.Constraint('Horizontal',18,2,11,2))
### End command Sketcher_ConstrainHorizontal
# Gui.Selection.clearSelection()
# Gui.runCommand('Std_Undo',0)
App.getDocument('Unnamed').getObject('Sketch').movePoint(18,2,App.Vector(8.323002,36.485912,0),0)
App.getDocument('Unnamed').getObject('Sketch').movePoint(19,2,App.Vector(0.192441,36.415821,0),0)
App.getDocument('Unnamed').getObject('Sketch').movePoint(19,0,App.Vector(0.210273,1.626095,0),1)
App.getDocument('Unnamed').getObject('Sketch').movePoint(18,2,App.Vector(8.603365,36.345734,0),0)
App.getDocument('Unnamed').getObject('Sketch').movePoint(17,2,App.Vector(6.220270,21.346251,0),0)
App.getDocument('Unnamed').getObject('Sketch').movePoint(19,2,App.Vector(2.084900,37.607372,0),0)
App.getDocument('Unnamed').getObject('Sketch').movePoint(18,2,App.Vector(6.360452,31.018812,0),0)
App.getDocument('Unnamed').getObject('Sketch').movePoint(11,2,App.Vector(18.065657,35.434547,0),0)
App.getDocument('Unnamed').getObject('Sketch').movePoint(19,2,App.Vector(0.402715,36.766277,0),0)
# Gui.Selection.addSelection('Unnamed','Body','Sketch.Constraint40',-0.0475124,34.9262,0.00900269,False)
App.getDocument('Unnamed').getObject('Sketch').movePoint(19,2,App.Vector(0.648685,34.333179,0),0)
# Gui.Selection.addSelection('Unnamed','Body','Sketch.Edge20',2.42785,35,0.008,False)
# Gui.Selection.clearSelection()
# Gui.Selection.addSelection('Unnamed','Body','Sketch.Constraint40',-5.00488e-05,34.9999,0.00900269,False)
### Begin command Std_Delete
App.getDocument('Unnamed').getObject('Sketch').delConstraint(39)
App.getDocument('Unnamed').recompute()
### End command Std_Delete
# Gui.Selection.clearSelection()
App.getDocument('Unnamed').getObject('Sketch').movePoint(19,2,App.Vector(0.000508,35.000393,0),0)
App.getDocument('Unnamed').getObject('Sketch').movePoint(19,2,App.Vector(0.879232,36.236080,0),0)
# Gui.Selection.addSelection('Unnamed','Body','Sketch.Vertex40',0.879232,36.2361,0.011,False)
# Gui.Selection.addSelection('Unnamed','Body','Sketch.Edge1',0,33.9372,0.008,False)
### Begin command Sketcher_ConstrainCoincidentUnified
App.getDocument('Unnamed').getObject('Sketch').addConstraint(Sketcher.Constraint('PointOnObject',19,2,0))
### End command Sketcher_ConstrainCoincidentUnified
# Gui.Selection.clearSelection()
App.getDocument('Unnamed').getObject('Sketch').movePoint(18,0,App.Vector(0.125517,0.000000,0),1)
# Gui.runCommand('Sketcher_CompDimensionTools',0)
App.getDocument('Unnamed').getObject('Sketch').addConstraint(Sketcher.Constraint('Distance',11,1,11,2,2.934343)) 
# Gui.Selection.addSelection('Unnamed','Body','Sketch.Edge12',19.8911,37,0)
App.getDocument('Unnamed').getObject('Sketch').addConstraint(Sketcher.Constraint('DistanceX',11,2,11,1,2.934343)) 
App.getDocument('Unnamed').Sketch.setExpression('Constraints[48]', u'<<Spreadsheet>>.portr_xdist')
# Gui.Selection.clearSelection()
App.getDocument('Unnamed').getObject('Sketch').addConstraint(Sketcher.Constraint('Distance',19,1,19,2,6.485969)) 
# Gui.Selection.addSelection('Unnamed','Body','Sketch.Edge20',3.24298,36.2361,0)
App.getDocument('Unnamed').getObject('Sketch').addConstraint(Sketcher.Constraint('DistanceX',19,2,19,1,6.485969)) 
App.getDocument('Unnamed').Sketch.setExpression('Constraints[49]', u'<<Spreadsheet>>.portr_edge_xdist')
# Gui.Selection.clearSelection()
# Gui.runCommand('Sketcher_ConstrainEqual',0)
# Gui.Selection.addSelection('Unnamed','Body','Sketch.Edge18',7.83156,21.3463,0)
# Gui.Selection.addSelection('Unnamed','Body','Sketch.Edge14',15.9645,21.3405,0)
App.getDocument('Unnamed').getObject('Sketch').addConstraint(Sketcher.Constraint('Equal',17,13))
# Gui.Selection.clearSelection()
# Gui.Selection.addSelection('Unnamed','Body','Sketch.Edge17',7.7223,23.3204,0)
# Gui.Selection.addSelection('Unnamed','Body','Sketch.Edge15',14.2777,23.7343,0)
App.getDocument('Unnamed').getObject('Sketch').addConstraint(Sketcher.Constraint('Equal',16,14))
# Gui.Selection.clearSelection()
App.getDocument('Unnamed').getObject('Sketch').movePoint(15,2,App.Vector(8.911864,25.743103,0),0)
# Gui.runCommand('Sketcher_CompDimensionTools',0)
# Gui.Selection.addSelection('Unnamed','Body','Sketch.Edge19',5,31.0457,0.008,False)
# Gui.Selection.addSelection('Unnamed','Body','Sketch.Edge13',17,30.732,0.008,False)
### Begin command Sketcher_ConstrainEqual
App.getDocument('Unnamed').getObject('Sketch').addConstraint(Sketcher.Constraint('Equal',18,12))
### End command Sketcher_ConstrainEqual
# Gui.Selection.clearSelection()
# Gui.runCommand('Sketcher_CompDimensionTools',0)
App.getDocument('Unnamed').getObject('Sketch').addConstraint(Sketcher.Constraint('Distance',18,1,18,2,15.537821)) 
# Gui.Selection.addSelection('Unnamed','Body','Sketch.Edge19',5,26.9677,0)
App.getDocument('Unnamed').getObject('Sketch').addConstraint(Sketcher.Constraint('DistanceY',18,1,18,2,15.537821)) 
App.getDocument('Unnamed').Sketch.setExpression('Constraints[53]', u'<<Spreadsheet>>.left_portr_ydist')
# Gui.Selection.clearSelection()
App.getDocument('Unnamed').getObject('Sketch').movePoint(15,2,App.Vector(9.206934,29.907253,0),0)
App.getDocument('Unnamed').getObject('Sketch').movePoint(15,2,App.Vector(9.000777,31.012238,0),0)
App.getDocument('Unnamed').getObject('Sketch').movePoint(15,2,App.Vector(9.078753,31.004166,0),0)
# Gui.runCommand('Sketcher_Dimension',0)
App.getDocument('Unnamed').getObject('Sketch').addConstraint(Sketcher.Constraint('Distance',15,1,15,2,3.842494)) 
# Gui.Selection.addSelection('Unnamed','Body','Sketch.Edge16',11.1944,31.0042,0)
App.getDocument('Unnamed').getObject('Sketch').addConstraint(Sketcher.Constraint('DistanceX',15,2,15,1,3.842494)) 
App.getDocument('Unnamed').getObject('Sketch').setDatum(54,App.Units.Quantity('4.000000 mm'))
App.getDocument('Unnamed').getObject('Sketch').renameConstraint(54, u'TEMP')
# Gui.Selection.clearSelection()
App.getDocument('Unnamed').getObject('Sketch').movePoint(15,2,App.Vector(8.892781,30.898170,0),0)
# Gui.runCommand('Sketcher_CompDimensionTools',0)
App.getDocument('Unnamed').getObject('Sketch').addConstraint(Sketcher.Constraint('Distance',16,1,16,2,3.898170)) 
# Gui.Selection.addSelection('Unnamed','Body','Sketch.Edge17',9,28.6936,0)
App.getDocument('Unnamed').getObject('Sketch').addConstraint(Sketcher.Constraint('DistanceY',16,2,16,1,3.898170)) 
App.getDocument('Unnamed').getObject('Sketch').setDatum(55,App.Units.Quantity('4.000000 mm'))
# Gui.Selection.clearSelection()
# Gui.Selection.addSelection('Unnamed','Body','Sketch.Constraint56',7.57003,28.7881,0.009,False)
# Gui.Selection.removeSelection('Unnamed','Body','Sketch.Constraint56')
App.getDocument('Unnamed').getObject('Sketch').setDatum(55,App.Units.Quantity('4.000000 mm'))
App.getDocument('Unnamed').getObject('Sketch').renameConstraint(55, u'TEMPO')
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(0,App.Vector(-0.272362,7.572718,0))
App.getDocument('Unnamed').getObject('Sketch').trim(1,App.Vector(5.091623,0.293024,0))
App.getDocument('Unnamed').getObject('Sketch').movePoint(0,1,App.Vector(-0.574246,64.955032,0),0)
App.getDocument('Unnamed').getObject('Sketch').movePoint(3,0,App.Vector(7.875798,0.006721,0),1)
# Gui.Selection.addSelection('Unnamed','Body','Sketch.Vertex6',66.3016,75,0.014,False)
# Gui.Selection.addSelection('Unnamed','Body','Sketch.RootPoint',0,0,0.01,False)
### Begin command Sketcher_ConstrainCoincidentUnified
App.getDocument('Unnamed').getObject('Sketch').addConstraint(Sketcher.Constraint('Coincident',2,2,-1,1))
### End command Sketcher_ConstrainCoincidentUnified
# Gui.Selection.clearSelection()
# Gui.runCommand('Std_Undo',0)
App.getDocument('Unnamed').getObject('Sketch').movePoint(2,2,App.Vector(-5.340281,35.814259,0),0)
# Gui.Selection.addSelection('Unnamed','Body','Sketch.Vertex16',-5.34028,1.28675e-09,0.014,False)
# Gui.Selection.addSelection('Unnamed','Body','Sketch.RootPoint',0,0,0.01,False)
### Begin command Sketcher_ConstrainCoincidentUnified
App.getDocument('Unnamed').getObject('Sketch').addConstraint(Sketcher.Constraint('Coincident',7,1,-1,1))
### End command Sketcher_ConstrainCoincidentUnified
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CreatePolyline',0)
# Gui.runCommand('Sketcher_CreatePolyline',0)
# Gui.runCommand('Sketcher_CompCreateRectangles',0)
ActiveSketch = App.getDocument('Unnamed').getObject('Sketch')

lastGeoId = len(ActiveSketch.Geometry)

geoList = []
geoList.append(Part.LineSegment(App.Vector(0.000000, 58.679440, 0.000000),App.Vector(-9.948833, 58.679440, 0.000000)))
geoList.append(Part.LineSegment(App.Vector(-9.948833, 58.679440, 0.000000),App.Vector(-9.948833, 53.074345, 0.000000)))
geoList.append(Part.LineSegment(App.Vector(-9.948833, 53.074345, 0.000000),App.Vector(0.000000, 53.074345, 0.000000)))
geoList.append(Part.LineSegment(App.Vector(0.000000, 53.074345, 0.000000),App.Vector(0.000000, 58.679440, 0.000000)))
App.getDocument('Unnamed').getObject('Sketch').addGeometry(geoList,False)
del geoList

constraintList = []
constraintList.append(Sketcher.Constraint('Coincident', 20, 2, 21, 1))
constraintList.append(Sketcher.Constraint('Coincident', 21, 2, 22, 1))
constraintList.append(Sketcher.Constraint('Coincident', 22, 2, 23, 1))
constraintList.append(Sketcher.Constraint('Coincident', 23, 2, 20, 1))
constraintList.append(Sketcher.Constraint('Horizontal', 20))
constraintList.append(Sketcher.Constraint('Horizontal', 22))
constraintList.append(Sketcher.Constraint('Vertical', 21))
constraintList.append(Sketcher.Constraint('Vertical', 23))
App.getDocument('Unnamed').getObject('Sketch').addConstraint(constraintList)
del constraintList

App.getDocument('Unnamed').getObject('Sketch').addConstraint(Sketcher.Constraint('PointOnObject', 20, 1, 2))


# Gui.runCommand('Sketcher_CompDimensionTools',0)
App.getDocument('Unnamed').getObject('Sketch').addConstraint(Sketcher.Constraint('Distance',21,1,21,2,5.605095)) 
# Gui.Selection.addSelection('Unnamed','Body','Sketch.Edge22',-9.94883,54.8168,0)
App.getDocument('Unnamed').getObject('Sketch').addConstraint(Sketcher.Constraint('DistanceY',21,2,21,1,5.605095)) 
App.getDocument('Unnamed').Sketch.setExpression('Constraints[64]', u'<<Spreadsheet>>.edgecut_xdist')
# Gui.Selection.clearSelection()
# Gui.Selection.addSelection('Unnamed','Body','Sketch.Edge22',-9.94883,56.2181,0.008,False)
# Gui.Selection.addSelection('Unnamed','Body','Sketch.Edge21',-7.72215,58.2442,0.008,False)
# Gui.Selection.addSelection('Unnamed','Body','Sketch.Edge23',-7.08521,54.2442,0.008,False)
### Begin command Sketcher_ConstrainEqual
App.getDocument('Unnamed').getObject('Sketch').addConstraint(Sketcher.Constraint('Equal',21,20))
App.getDocument('Unnamed').getObject('Sketch').addConstraint(Sketcher.Constraint('Equal',20,22))
### End command Sketcher_ConstrainEqual
# Gui.Selection.clearSelection()
### Begin command Std_Delete
App.getDocument('Unnamed').getObject('Sketch').delConstraint(66)
App.getDocument('Unnamed').recompute()
### End command Std_Delete
# Gui.Selection.clearSelection()
# Gui.runCommand('Sketcher_CompDimensionTools',0)
App.getDocument('Unnamed').getObject('Sketch').addConstraint(Sketcher.Constraint('Distance',22,1,22,2,4.000000)) 
# Gui.Selection.addSelection('Unnamed','Body','Sketch.Edge23',-2.35573,55.137,0)
App.getDocument('Unnamed').getObject('Sketch').addConstraint(Sketcher.Constraint('DistanceX',22,1,22,2,4.000000)) 
App.getDocument('Unnamed').getObject('Sketch').addConstraint(Sketcher.Constraint('Distance',22,1,22,2,4.000000)) 
App.getDocument('Unnamed').getObject('Sketch').addConstraint(Sketcher.Constraint('Distance',-1,1,22,55.137036)) 
# Gui.Selection.addSelection('Unnamed','Body','Sketch.H_Axis',-25.2857,0,0)
App.getDocument('Unnamed').Sketch.setExpression('Constraints[66]', u'<<Spreadsheet>>.edgecut_ydist')
# Gui.Selection.clearSelection()
# Gui.runCommand('Sketcher_CompCurveEdition',0)
App.getDocument('Unnamed').getObject('Sketch').trim(2,App.Vector(0.279568,58.798248,0))
App.getDocument('Unnamed').getObject('Sketch').trim(23,App.Vector(0.000000,57.000000,0))
App.getDocument('Unnamed').getObject('Sketch').trim(23,App.Vector(0.000000,58.798248,0))
# Gui.runCommand('Std_Undo',0)
# Gui.runCommand('Std_Undo',0)
# Gui.runCommand('Std_Undo',0)
# Gui.runCommand('Sketcher_CompCurveEdition',0)
App.getDocument('Unnamed').getObject('Sketch').trim(2,App.Vector(-0.042383,58.846272,0))
App.getDocument('Unnamed').getObject('Sketch').movePoint(3,1,App.Vector(-0.320855,71.225410,0),0)
App.getDocument('Unnamed').getObject('Sketch').movePoint(3,1,App.Vector(-2.202995,73.107544,0),0)
# Gui.Selection.addSelection('Unnamed','Body','Sketch.Vertex7',-2.203,75,0.014,False)
# Gui.Selection.addSelection('Unnamed','Body','Sketch.V_Axis',0,74.9897,0.002,False)
### Begin command Sketcher_ConstrainCoincidentUnified
App.getDocument('Unnamed').getObject('Sketch').addConstraint(Sketcher.Constraint('PointOnObject',3,1,-2))
### End command Sketcher_ConstrainCoincidentUnified
# Gui.Selection.clearSelection()
App.getDocument('Unnamed').getObject('Sketch').movePoint(24,1,App.Vector(-1.808001,60.092087,0),0)
# Gui.Selection.addSelection('Unnamed','Body','Sketch.Edge24',-1.808,59.3404,0.008,False)
### Begin command Std_Delete
App.getDocument('Unnamed').getObject('Sketch').delGeometries([23])
App.getDocument('Unnamed').recompute()
### End command Std_Delete
# Gui.Selection.clearSelection()
# Gui.Selection.addSelection('Unnamed','Body','Sketch.Vertex41',-1.808,61,0.014,False)
# Gui.Selection.addSelection('Unnamed','Body','Sketch.V_Axis',0,60.7029,0.002,False)
### Begin command Sketcher_ConstrainCoincidentUnified
App.getDocument('Unnamed').getObject('Sketch').addConstraint(Sketcher.Constraint('PointOnObject',20,1,-2))
### End command Sketcher_ConstrainCoincidentUnified
# Gui.Selection.clearSelection()
# Gui.Selection.addSelection('Unnamed','Body','Sketch.Vertex46',-1.808,57,0.014,False)
# Gui.Selection.addSelection('Unnamed','Body','Sketch.Edge3',0,56.4965,0.008,False)
### Begin command Sketcher_ConstrainCoincidentUnified
App.getDocument('Unnamed').getObject('Sketch').addConstraint(Sketcher.Constraint('PointOnObject',22,2,2))
### End command Sketcher_ConstrainCoincidentUnified
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# Gui.Selection.addSelection('Unnamed','Body','Sketch.')
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(0,1,App.Vector(-57.437222,64.103195,0),0)
# Gui.runCommand('Sketcher_CreatePolyline',0)
App.getDocument('Unnamed').getObject('Sketch').addGeometry(Part.LineSegment(App.Vector(-43.120625,75.000000,0),App.Vector(-42.779060,52.439297,0)),False)
App.getDocument('Unnamed').getObject('Sketch').addConstraint(Sketcher.Constraint('PointOnObject',24,1,3)) 
App.getDocument('Unnamed').getObject('Sketch').addConstraint(Sketcher.Constraint('Vertical',24)) 
App.getDocument('Unnamed').getObject('Sketch').addGeometry(Part.LineSegment(App.Vector(-43.120625,52.439297,0),App.Vector(-38.765678,52.353909,0)),False)
App.getDocument('Unnamed').getObject('Sketch').addConstraint(Sketcher.Constraint('Coincident',24,2,25,1)) 
App.getDocument('Unnamed').getObject('Sketch').addConstraint(Sketcher.Constraint('Horizontal',25)) 
App.getDocument('Unnamed').getObject('Sketch').addGeometry(Part.LineSegment(App.Vector(-38.765678,52.439297,0),App.Vector(-38.680286,49.535999,0)),False)
App.getDocument('Unnamed').getObject('Sketch').addConstraint(Sketcher.Constraint('Coincident',25,2,26,1)) 
App.getDocument('Unnamed').getObject('Sketch').addConstraint(Sketcher.Constraint('Vertical',26)) 
App.getDocument('Unnamed').getObject('Sketch').addGeometry(Part.LineSegment(App.Vector(-38.765678,49.535999,0),App.Vector(-31.763609,49.535999,0)),False)
App.getDocument('Unnamed').getObject('Sketch').addConstraint(Sketcher.Constraint('Coincident',26,2,27,1)) 
App.getDocument('Unnamed').getObject('Sketch').addConstraint(Sketcher.Constraint('Horizontal',27)) 
App.getDocument('Unnamed').getObject('Sketch').addGeometry(Part.LineSegment(App.Vector(-31.763609,49.535999,0),App.Vector(-31.763609,52.353909,0)),False)
App.getDocument('Unnamed').getObject('Sketch').addConstraint(Sketcher.Constraint('Coincident',27,2,28,1)) 
App.getDocument('Unnamed').getObject('Sketch').addConstraint(Sketcher.Constraint('Vertical',28)) 
App.getDocument('Unnamed').getObject('Sketch').addGeometry(Part.LineSegment(App.Vector(-31.763609,52.353909,0),App.Vector(-27.750227,52.439297,0)),False)
App.getDocument('Unnamed').getObject('Sketch').addConstraint(Sketcher.Constraint('Coincident',28,2,29,1)) 
App.getDocument('Unnamed').getObject('Sketch').addConstraint(Sketcher.Constraint('Horizontal',29)) 
App.getDocument('Unnamed').getObject('Sketch').addGeometry(Part.LineSegment(App.Vector(-27.750227,52.353909,0),App.Vector(-27.000000,75.000000,0)),False)
App.getDocument('Unnamed').getObject('Sketch').addConstraint(Sketcher.Constraint('Coincident',29,2,30,1)) 
App.getDocument('Unnamed').getObject('Sketch').addConstraint(Sketcher.Constraint('Symmetric',3,1,3,2,30,2)) 
App.getDocument('Unnamed').getObject('Sketch').addConstraint(Sketcher.Constraint('Vertical',30)) 
# Gui.runCommand('Sketcher_CompDimensionTools',0)
App.getDocument('Unnamed').getObject('Sketch').addConstraint(Sketcher.Constraint('Distance',27,1,27,2,7.002069)) 
# Gui.Selection.addSelection('Unnamed','Body','Sketch.Edge28',-35.2646,49.536,0)
App.getDocument('Unnamed').getObject('Sketch').addConstraint(Sketcher.Constraint('DistanceX',27,1,27,2,7.002069)) 
App.getDocument('Unnamed').Sketch.setExpression('Constraints[84]', u'<<Spreadsheet>>.inner_dip_len')
# Gui.Selection.clearSelection()
App.getDocument('Unnamed').getObject('Sketch').addConstraint(Sketcher.Constraint('Distance',28,1,28,2,2.817910)) 
# Gui.Selection.addSelection('Unnamed','Body','Sketch.Edge29',-31.4808,50.945,0)
App.getDocument('Unnamed').getObject('Sketch').addConstraint(Sketcher.Constraint('DistanceY',28,1,28,2,2.817910)) 
App.getDocument('Unnamed').Sketch.setExpression('Constraints[85]', u'<<Spreadsheet>>.inner_dip_depth')
# Gui.Selection.clearSelection()
# Gui.Selection.addSelection('Unnamed','Body','Sketch.Edge27',-39.4808,50.5038,0.008,False)
# Gui.Selection.addSelection('Unnamed','Body','Sketch.Edge29',-31.4808,51.203,0.008,False)
### Begin command Sketcher_ConstrainEqual
App.getDocument('Unnamed').getObject('Sketch').addConstraint(Sketcher.Constraint('Equal',26,28))
### End command Sketcher_ConstrainEqual
# Gui.Selection.clearSelection()
# Gui.Selection.addSelection('Unnamed','Body','Sketch.Edge26',-40.4721,53.2297,0.008,False)
# Gui.Selection.addSelection('Unnamed','Body','Sketch.Edge30',-28.4472,53.2297,0.008,False)
### Begin command Sketcher_ConstrainEqual
App.getDocument('Unnamed').getObject('Sketch').addConstraint(Sketcher.Constraint('Equal',25,29))
### End command Sketcher_ConstrainEqual
# Gui.Selection.clearSelection()
# Gui.runCommand('Sketcher_CompDimensionTools',0)
App.getDocument('Unnamed').getObject('Sketch').addConstraint(Sketcher.Constraint('Distance',24,1,24,2,21.770281)) 
# Gui.Selection.addSelection('Unnamed','Body','Sketch.Edge25',-43.5884,68.3504,0)
App.getDocument('Unnamed').getObject('Sketch').addConstraint(Sketcher.Constraint('DistanceY',24,2,24,1,21.770281)) 
App.getDocument('Unnamed').getObject('Sketch').addConstraint(Sketcher.Constraint('Distance',30,1,24,16.588436)) 
# Gui.Selection.addSelection('Unnamed','Body','Sketch.Edge31',-27,68.8599,0)
App.getDocument('Unnamed').Sketch.setExpression('Constraints[88]', u'<<Spreadsheet>>.topmid_xdist')
# Gui.Selection.clearSelection()
App.getDocument('Unnamed').getObject('Sketch').addConstraint(Sketcher.Constraint('Distance',30,1,30,2,21.770281)) 
# Gui.Selection.addSelection('Unnamed','Body','Sketch.Edge31',-27,68.7579,0)
App.getDocument('Unnamed').getObject('Sketch').addConstraint(Sketcher.Constraint('DistanceY',30,1,30,2,21.770281)) 
App.getDocument('Unnamed').getObject('Sketch').addConstraint(Sketcher.Constraint('Distance',23,1,30,27.000000)) 
# Gui.Selection.addSelection('Unnamed','Body','Sketch.Edge24',0,66.4774,0)
App.getDocument('Unnamed').Sketch.setExpression('Constraints[89]', u'<<Spreadsheet>>.topright_xdist')
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Std_Undo',0)
# Gui.runCommand('Std_Undo',0)
# Gui.runCommand('Std_Undo',0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompDimensionTools',0)
App.getDocument('Unnamed').getObject('Sketch').addConstraint(Sketcher.Constraint('Distance',30,1,30,2,21.770281)) 
# Gui.Selection.addSelection('Unnamed','Body','Sketch.Edge31',-27,67.1312,0)
App.getDocument('Unnamed').getObject('Sketch').addConstraint(Sketcher.Constraint('DistanceY',30,1,30,2,21.770281)) 
App.getDocument('Unnamed').getObject('Sketch').addConstraint(Sketcher.Constraint('Distance',23,1,30,27.000000)) 
# Gui.Selection.addSelection('Unnamed','Body','Sketch.Edge24',-0,68,0)
App.getDocument('Unnamed').Sketch.setExpression('Constraints[88]', u'<<Spreadsheet>>.topright_xdist')
# Gui.Selection.clearSelection()
# Gui.Selection.clearSelection()
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(3,App.Vector(-33.066975,75.694328,0))
# Gui.Selection.addSelection('Unnamed','Body','Sketch.Constraint89',-18.8286,66.922,0.009,False)
App.getDocument('Unnamed').getObject('Sketch').movePoint(23,1,App.Vector(-4.960431,60.820034,0),0)
### Begin command Std_Delete
App.getDocument('Unnamed').getObject('Sketch').delConstraint(88)
App.getDocument('Unnamed').recompute()
### End command Std_Delete
# Gui.Selection.clearSelection()
App.getDocument('Unnamed').getObject('Sketch').movePoint(4,1,App.Vector(-49.164921,75.399300,0),0)
App.getDocument('Unnamed').getObject('Sketch').movePoint(5,1,App.Vector(-59.095573,71.852631,0),0)
App.getDocument('Unnamed').getObject('Sketch').movePoint(0,0,App.Vector(0.000000,-5.175003,0),1)
App.getDocument('Unnamed').getObject('Sketch').movePoint(24,1,App.Vector(-45.123131,68.592026,0),0)
App.getDocument('Unnamed').getObject('Sketch').movePoint(4,1,App.Vector(-54.940666,72.935303,0),0)
# Gui.Selection.addSelection('Unnamed','Body','Sketch.Vertex8',-27.4703,61,0.014,False)
# Gui.Selection.addSelection('Unnamed','Body','Sketch.Vertex62',-27.4703,66.9677,0.014,False)
### Begin command Sketcher_ConstrainCoincidentUnified
App.getDocument('Unnamed').getObject('Sketch').addConstraint(Sketcher.Constraint('Coincident',3,2,30,2))
### End command Sketcher_ConstrainCoincidentUnified
# Gui.Selection.clearSelection()
# Gui.runCommand('Std_Undo',0)
# Gui.Selection.addSelection('Unnamed','Body','Sketch.Constraint83',-27.3756,66.896,0.00900269,False)
### Begin command Std_Delete
App.getDocument('Unnamed').getObject('Sketch').delConstraint(82)
App.getDocument('Unnamed').recompute()
### End command Std_Delete
# Gui.Selection.clearSelection()
# Gui.Selection.addSelection('Unnamed','Body','Sketch.Constraint88',-27.8712,60.9488,0.00900269,False)
### Begin command Std_Delete
App.getDocument('Unnamed').getObject('Sketch').delConstraint(87)
App.getDocument('Unnamed').recompute()
### End command Std_Delete
# Gui.Selection.clearSelection()
# Gui.Selection.addSelection('Unnamed','Body','Sketch.Vertex8',-27.4703,61,0.014,False)
# Gui.Selection.addSelection('Unnamed','Body','Sketch.Vertex62',-27.4703,66.9677,0.014,False)
### Begin command Sketcher_ConstrainCoincidentUnified
App.getDocument('Unnamed').getObject('Sketch').addConstraint(Sketcher.Constraint('Coincident',3,2,30,2))
### End command Sketcher_ConstrainCoincidentUnified
# Gui.Selection.clearSelection()
# Gui.Selection.addSelection('Unnamed','Body','Sketch.Edge31',-27.4703,56.9268,0.008,False)
# Gui.Selection.addSelection('Unnamed','Body','Sketch.Edge25',-45.3668,58.7659,0.008,False)
### Begin command Sketcher_ConstrainEqual
App.getDocument('Unnamed').getObject('Sketch').addConstraint(Sketcher.Constraint('Equal',30,24))
### End command Sketcher_ConstrainEqual
# Gui.Selection.clearSelection()
# Gui.Selection.addSelection('Unnamed','Body','Sketch.Vertex12',-59,75,0.014,False)
# Gui.Selection.addSelection('Unnamed','Body','Sketch.Vertex49',-45.4137,61,0.014,False)
### Begin command Sketcher_ConstrainCoincidentUnified
App.getDocument('Unnamed').getObject('Sketch').addConstraint(Sketcher.Constraint('Coincident',5,1,24,1))
### End command Sketcher_ConstrainCoincidentUnified
# Gui.Selection.clearSelection()
# Gui.runCommand('Std_Undo',0)
# Gui.Selection.addSelection('Unnamed','Body','Sketch.Constraint6',-129.294,38.2645,0.009,False)
### Begin command Std_Delete
App.getDocument('Unnamed').getObject('Sketch').delConstraint(5)
App.getDocument('Unnamed').recompute()
### End command Std_Delete
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(3,0,App.Vector(-2.538387,4.175339,0),1)
App.getDocument('Unnamed').getObject('Sketch').movePoint(3,2,App.Vector(-29.812038,63.707184,0),0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(0,1,App.Vector(-58.662437,65.181007,0),0)
# Gui.Selection.addSelection('Unnamed','Body','Sketch.Edge1',-59,63.7208,0.008,False)
# Gui.Selection.addSelection('Unnamed','Body','Sketch.Edge5',-56.1289,74.5241,0.008,False)
# Gui.Selection.addSelection('Unnamed','Body','Sketch.Edge4',-50.8402,75,0.008,False)
# Gui.Selection.clearSelection()
# Gui.runCommand('Sketcher_CompCurveEdition',0)
App.getDocument('Unnamed').getObject('Sketch').movePoint(24,0,App.Vector(-0.987946,-4.604370,0),1)
App.getDocument('Unnamed').getObject('Sketch').movePoint(24,0,App.Vector(0.422852,-0.046982,0),1)
App.getDocument('Unnamed').getObject('Sketch').movePoint(24,2,App.Vector(-44.971798,47.593407,0),0)
# Gui.runCommand('Sketcher_ConstrainBlock',0)
# Gui.Selection.addSelection('Unnamed','Body','Sketch.Edge25',-44.9718,68.6211,0)
App.getDocument('Unnamed').getObject('Sketch').addConstraint(Sketcher.Constraint('Block',24))
# Gui.Selection.clearSelection()
# Gui.runCommand('Std_Undo',0)
# Gui.runCommand('Sketcher_CompDimensionTools',0)
App.getDocument('Unnamed').getObject('Sketch').addConstraint(Sketcher.Constraint('Distance',30,1,30,2,27.406593)) 
# Gui.Selection.addSelection('Unnamed','Body','Sketch.Edge31',-27,68.8116,0)
App.getDocument('Unnamed').getObject('Sketch').addConstraint(Sketcher.Constraint('DistanceY',30,1,30,2,27.406593)) 
App.getDocument('Unnamed').getObject('Sketch').addConstraint(Sketcher.Constraint('Distance',23,1,30,27.000000)) 
# Gui.Selection.addSelection('Unnamed','Body','Sketch.Edge24',4.30573e-29,67.0968,0)
App.getDocument('Unnamed').Sketch.setExpression('Constraints[88]', u'<<Spreadsheet>>.topright_xdist')
# Gui.Selection.clearSelection()
# Gui.runCommand('Std_Undo',0)
App.getDocument('Unnamed').getObject('Sketch').movePoint(30,0,App.Vector(7.411386,-1.333694,0),1)
App.getDocument('Unnamed').getObject('Sketch').movePoint(30,2,App.Vector(-21.112822,73.384232,0),0)
# Gui.Selection.addSelection('Unnamed','Body','Sketch.Constraint83',-27.0722,74.929,0.00900269,False)
### Begin command Std_Delete
App.getDocument('Unnamed').getObject('Sketch').delConstraint(82)
App.getDocument('Unnamed').recompute()
### End command Std_Delete
# Gui.Selection.clearSelection()
App.getDocument('Unnamed').getObject('Sketch').movePoint(30,2,App.Vector(-25.782541,74.780022,0),0)
App.getDocument('Unnamed').getObject('Sketch').movePoint(24,1,App.Vector(-39.641518,75.000000,0),0)
App.getDocument('Unnamed').getObject('Sketch').movePoint(30,2,App.Vector(-16.742138,75.020103,0),0)
App.getDocument('Unnamed').getObject('Sketch').movePoint(24,1,App.Vector(-34.936165,75.000000,0),0)
App.getDocument('Unnamed').getObject('Sketch').movePoint(30,2,App.Vector(-14.232613,72.719704,0),0)
# Gui.Selection.addSelection('Unnamed','Body','Sketch.Vertex62',-14.2326,72.7197,0.014,False)
# Gui.Selection.addSelection('Unnamed','Body','Sketch.Edge4',-13.8144,75,0.008,False)
### Begin command Sketcher_ConstrainCoincidentUnified
App.getDocument('Unnamed').getObject('Sketch').addConstraint(Sketcher.Constraint('PointOnObject',30,2,3))
### End command Sketcher_ConstrainCoincidentUnified
# Gui.Selection.clearSelection()
# Gui.runCommand('Sketcher_Dimension',0)
App.getDocument('Unnamed').getObject('Sketch').addConstraint(Sketcher.Constraint('Distance',30,1,30,2,28.740287)) 
# Gui.Selection.addSelection('Unnamed','Body','Sketch.Edge31',-14.2326,66.4315,0)
App.getDocument('Unnamed').getObject('Sketch').addConstraint(Sketcher.Constraint('DistanceY',30,1,30,2,28.740287)) 
App.getDocument('Unnamed').getObject('Sketch').addConstraint(Sketcher.Constraint('Distance',23,1,30,14.232613)) 
# Gui.Selection.addSelection('Unnamed','Body','Sketch.Edge24',-0,66.0505,0)
App.getDocument('Unnamed').Sketch.setExpression('Constraints[88]', u'<<Spreadsheet>>.topright_xdist')
# Gui.Selection.clearSelection()
App.getDocument('Unnamed').getObject('Sketch').addConstraint(Sketcher.Constraint('Distance',24,1,24,2,28.740287)) 
# Gui.Selection.addSelection('Unnamed','Body','Sketch.Edge25',-36.4391,63.0027,0)
App.getDocument('Unnamed').getObject('Sketch').addConstraint(Sketcher.Constraint('DistanceY',24,2,24,1,28.740287)) 
App.getDocument('Unnamed').getObject('Sketch').addConstraint(Sketcher.Constraint('Distance',30,1,24,18.439088)) 
# Gui.Selection.addSelection('Unnamed','Body','Sketch.Edge31',-18,60.6299,0)
App.getDocument('Unnamed').Sketch.setExpression('Constraints[89]', u'<<Spreadsheet>>.topmid_xdist')
# Gui.Selection.clearSelection()
App.getDocument('Unnamed').getObject('Sketch').movePoint(24,2,App.Vector(-40.342697,46.265087,0),0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(27,0,App.Vector(0.000000,4.791359,0),1)
# Gui.runCommand('Sketcher_CompCreateConic',0)
ActiveSketch = App.getDocument('Unnamed').getObject('Sketch')

lastGeoId = len(ActiveSketch.Geometry)

geoList = []
geoList.append(Part.Circle(App.Vector(-16.147842, 37.453777, 0.000000), App.Vector(0.000000, 0.000000, 1.000000), 6.642775))
App.getDocument('Unnamed').getObject('Sketch').addGeometry(geoList,False)
del geoList

constraintList = []
constraintList = []
ActiveSketch = App.getDocument('Unnamed').getObject('Sketch')

lastGeoId = len(ActiveSketch.Geometry)

geoList = []
geoList.append(Part.Circle(App.Vector(-16.147842, 37.453777, 0.000000), App.Vector(0.000000, 0.000000, 1.000000), 4.405031))
App.getDocument('Unnamed').getObject('Sketch').addGeometry(geoList,False)
del geoList

constraintList = []
App.getDocument('Unnamed').getObject('Sketch').addConstraint(Sketcher.Constraint('Coincident', 32, 3, 31, 3))


# Gui.runCommand('Sketcher_CompDimensionTools',0)
App.getDocument('Unnamed').getObject('Sketch').addConstraint(Sketcher.Constraint('Diameter',32,8.810062)) 
# Gui.Selection.addSelection('Unnamed','Body','Sketch.Edge33',-12.3143,39.6237,0)
App.getDocument('Unnamed').Sketch.setExpression('Constraints[91]', u'<<Spreadsheet>>.gear_inner_rad')
# Gui.Selection.clearSelection()
App.getDocument('Unnamed').getObject('Sketch').addConstraint(Sketcher.Constraint('Diameter',31,13.285550)) 
# Gui.Selection.addSelection('Unnamed','Body','Sketch.Edge32',-9.72018,35.777,0)
App.getDocument('Unnamed').Sketch.setExpression('Constraints[92]', u'<<Spreadsheet>>.gear_outer_rad')
# Gui.Selection.clearSelection()
# Gui.Selection.addSelection('Unnamed','Body','Sketch.Vertex63',-16.1478,37.4538,0.014,False)
# Gui.Selection.addSelection('Unnamed','Body','Sketch.Vertex18',-17,15,0.014,False)
### Begin command Sketcher_ConstrainVertical
App.getDocument('Unnamed').getObject('Sketch').addConstraint(Sketcher.Constraint('Vertical',31,3,8,2))
### End command Sketcher_ConstrainVertical
# Gui.Selection.clearSelection()
# Gui.Selection.addSelection('Unnamed','Body','Sketch.Vertex22',-38,37,0.014,False)
# Gui.Selection.addSelection('Unnamed','Body','Sketch.Vertex63',-17,37.4538,0.014,False)
### Begin command Sketcher_ConstrainHorizontal
App.getDocument('Unnamed').getObject('Sketch').addConstraint(Sketcher.Constraint('Horizontal',10,2,31,3))
### End command Sketcher_ConstrainHorizontal
# Gui.Selection.clearSelection()
App.getDocument('Unnamed').getObject('Sketch').movePoint(28,0,App.Vector(-1.900209,0.228954,0),1)
App.getDocument('Unnamed').getObject('Sketch').movePoint(27,0,App.Vector(0.114479,0.723092,0),1)
App.getDocument('Unnamed').getObject('Sketch').movePoint(27,0,App.Vector(0.232121,3.118198,0),1)
# Gui.runCommand('Sketcher_ConstrainBlock',0)
# Gui.Selection.addSelection('Unnamed','Body','Sketch.Edge25',-40,61.2553,0)
App.getDocument('Unnamed').getObject('Sketch').addConstraint(Sketcher.Constraint('Block',24))
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(3,App.Vector(-34.506176,75.216362,0))
# Gui.Selection.addSelection('Unnamed','Body','Sketch.Edge34',-44.5052,75,0.008,False)
### Begin command Sketcher_ConstrainHorizontal
App.getDocument('Unnamed').getObject('Sketch').addConstraint(Sketcher.Constraint('Horizontal',33))
### End command Sketcher_ConstrainHorizontal
# Gui.Selection.clearSelection()
App.getDocument('Unnamed').getObject('Sketch').movePoint(24,1,App.Vector(-39.277046,71.914467,0),0)
App.getDocument('Unnamed').getObject('Sketch').movePoint(4,1,App.Vector(-54.334164,71.600777,0),0)
# Gui.runCommand('Std_Undo',0)
# Gui.Selection.addSelection('Unnamed','Body','Sketch.Edge4',-8.11718,75,0.008,False)
App.getDocument('Unnamed').getObject('Sketch').movePoint(3,2,App.Vector(-18.000000,74.423988,0),0)
# Gui.Selection.addSelection('Unnamed','Body','Sketch.Vertex12',-59,75,0.014,False)
# Gui.Selection.removeSelection('Unnamed','Body','Sketch.Edge4')
# Gui.Selection.clearSelection()
# Gui.Selection.addSelection('Unnamed','Body','Sketch.Vertex12',-59,75,0.014,False)
# Gui.Selection.addSelection('Unnamed','Body','Sketch.Vertex8',-18,74.424,0.014,False)
### Begin command Sketcher_ConstrainHorizontal
App.getDocument('Unnamed').getObject('Sketch').addConstraint(Sketcher.Constraint('Horizontal',5,1,3,2))
### End command Sketcher_ConstrainHorizontal
# Gui.Selection.clearSelection()
App.getDocument('Unnamed').getObject('Sketch').movePoint(33,0,App.Vector(-0.203518,-2.719948,0),1)
App.getDocument('Unnamed').getObject('Sketch').movePoint(0,1,App.Vector(-58.635132,66.945297,0),0)
# Gui.Selection.addSelection('Unnamed','Body','Sketch.Edge34',-51.0141,75,0.008,False)
# Gui.Selection.addSelection('Unnamed','Body','Sketch.Edge5',-55.395,74.8015,0.008,False)
### Begin command Std_Delete
App.getDocument('Unnamed').getObject('Sketch').delGeometries([4,33])
App.getDocument('Unnamed').recompute()
### End command Std_Delete
# Gui.Selection.clearSelection()
App.getDocument('Unnamed').getObject('Sketch').movePoint(0,1,App.Vector(-59.532372,58.931419,0),0)
App.ActiveDocument.recompute()
# Gui.Selection.addSelection('Unnamed','Body','Sketch.')
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(0,1,App.Vector(-59.000000,67.521492,0),0)
# Gui.runCommand('Sketcher_CreatePolyline',0)
App.getDocument('Unnamed').getObject('Sketch').addGeometry(Part.ArcOfCircle(Part.Circle(App.Vector(-54.053763,67.521492,0),App.Vector(0,0,1),4.946237),2.100034,3.141593),False)
App.getDocument('Unnamed').getObject('Sketch').addConstraint(Sketcher.Constraint('Tangent',0,1,32,2)) 
App.getDocument('Unnamed').getObject('Sketch').addGeometry(Part.LineSegment(App.Vector(-56.550997,71.791045,0),App.Vector(-40.000000,75.000000,0)),False)
App.getDocument('Unnamed').getObject('Sketch').addConstraint(Sketcher.Constraint('Coincident',32,1,33,1)) 
App.getDocument('Unnamed').getObject('Sketch').addConstraint(Sketcher.Constraint('Coincident',33,2,23,1)) 
# Gui.Selection.addSelection('Unnamed','Body','Sketch.Edge34',-54.7426,72.1417,0.008,False)
# Gui.Selection.addSelection('Unnamed','Body','Sketch.Edge33',-57.303,71.2508,0.008,False)
### Begin command Sketcher_ConstrainTangent
App.getDocument('Unnamed').getObject('Sketch').addConstraint(Sketcher.Constraint('Tangent',32,1,33,1))
App.getDocument('Unnamed').getObject('Sketch').delConstraintOnPoint(32,1)
### End command Sketcher_ConstrainTangent
# Gui.Selection.clearSelection()
# Gui.Selection.addSelection('Unnamed','Body','Sketch.Edge34',-44.4476,74.2154,0.008,False)
### Begin command Std_Delete
App.getDocument('Unnamed').getObject('Sketch').delGeometries([33])
App.getDocument('Unnamed').recompute()
### End command Std_Delete
# Gui.Selection.clearSelection()
# Gui.Selection.addSelection('Unnamed','Body','Sketch.Vertex46',-40,75,0.014,False)
### Begin command Std_Delete
App.getDocument('Unnamed').recompute()
### End command Std_Delete
# Gui.Selection.clearSelection()
# Gui.runCommand('Sketcher_CreatePolyline',0)
App.getDocument('Unnamed').getObject('Sketch').addGeometry(Part.LineSegment(App.Vector(-54.927244,72.366681,0),App.Vector(-44.190113,74.987122,0)),False)
App.getDocument('Unnamed').getObject('Sketch').addConstraint(Sketcher.Constraint('Coincident',32,1,33,1)) 
App.getDocument('Unnamed').getObject('Sketch').addGeometry(Part.LineSegment(App.Vector(-44.190113,74.987122,0),App.Vector(-40.000000,71.687416,0)),False)
App.getDocument('Unnamed').getObject('Sketch').addConstraint(Sketcher.Constraint('Coincident',33,2,34,1)) 
App.getDocument('Unnamed').getObject('Sketch').addConstraint(Sketcher.Constraint('PointOnObject',34,2,23)) 
# Gui.Selection.addSelection('Unnamed','Body','Sketch.Edge33',-56.7123,71.6742,0.008,False)
# Gui.Selection.addSelection('Unnamed','Body','Sketch.Edge34',-53.706,72.6647,0.008,False)
### Begin command Sketcher_ConstrainTangent
App.getDocument('Unnamed').getObject('Sketch').addConstraint(Sketcher.Constraint('Tangent',32,1,33,1))
App.getDocument('Unnamed').getObject('Sketch').delConstraintOnPoint(32,1)
### End command Sketcher_ConstrainTangent
# Gui.Selection.clearSelection()
# Gui.Selection.addSelection('Unnamed','Body','Sketch.Edge6',-1.69344,1.24944,0.008,False)
# Gui.Selection.addSelection('Unnamed','Body','Sketch.Edge33',-58.3342,70.0595,0.008,False)
### Begin command Sketcher_ConstrainEqual
App.getDocument('Unnamed').getObject('Sketch').addConstraint(Sketcher.Constraint('Equal',5,32))
### End command Sketcher_ConstrainEqual
# Gui.Selection.clearSelection()
# Gui.runCommand('Sketcher_CompDimensionTools',0)
App.getDocument('Unnamed').getObject('Sketch').addConstraint(Sketcher.Constraint('Distance',34,1,34,2,5.331789)) 
# Gui.Selection.addSelection('Unnamed','Body','Sketch.Edge35',-42.6154,73.7461,0)
App.getDocument('Unnamed').getObject('Sketch').addConstraint(Sketcher.Constraint('DistanceX',34,1,34,2,4.189629)) 
App.getDocument('Unnamed').getObject('Sketch').addConstraint(Sketcher.Constraint('Distance',34,1,34,2,5.331789)) 
App.getDocument('Unnamed').Sketch.setExpression('Constraints[96]', u'<<Spreadsheet>>.slant_len')
# Gui.Selection.clearSelection()
# Gui.Selection.addSelection('Unnamed','Body','Sketch.Vertex66',-42.1176,74.3991,0.014,False)
# Gui.Selection.addSelection('Unnamed','Body','Sketch.Vertex46',-40,75,0.014,False)
### Begin command Sketcher_ConstrainHorizontal
App.getDocument('Unnamed').getObject('Sketch').addConstraint(Sketcher.Constraint('Horizontal',33,2,23,1))
### End command Sketcher_ConstrainHorizontal
# Gui.Selection.clearSelection()
App.getDocument('Unnamed').getObject('Sketch').movePoint(32,3,App.Vector(-52.894966,66.984268,0),0)
# Gui.runCommand('Sketcher_CompDimensionTools',0)
App.getDocument('Unnamed').getObject('Sketch').addConstraint(Sketcher.Constraint('Radius',32,6.105034)) 
# Gui.Selection.addSelection('Unnamed','Body','Sketch.Edge33',-57.5587,70.924,0)
App.getDocument('Unnamed').Sketch.setExpression('Constraints[98]', u'<<Spreadsheet>>.fillet_rad')
# Gui.Selection.clearSelection()
App.getDocument('Unnamed').getObject('Sketch').movePoint(0,1,App.Vector(-58.544258,65.247246,0),0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(23,App.Vector(-40.047981,74.665573,0))
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# Gui.Selection.addSelection('Unnamed','Body','Sketch.')
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(33,2,App.Vector(-42.990734,74.099213,0),0)
App.getDocument('Unnamed').getObject('Sketch').movePoint(0,1,App.Vector(-59.000000,66.926361,0),0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# Gui.Selection.addSelection('Unnamed','Body','Sketch.')
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_ConstrainBlock',0)
# Gui.Selection.addSelection('Unnamed','Body','Sketch.Edge33',-58.8106,68.2896,0)
App.getDocument('Unnamed').getObject('Sketch').addConstraint(Sketcher.Constraint('Block',32))
# Gui.Selection.clearSelection()
# Gui.Selection.addSelection('Unnamed','Body','Sketch.Edge32',-14.6673,39.1906,0.008,False)
# Gui.runCommand('Sketcher_ConstrainCoincidentUnified',0)
# Gui.Selection.clearSelection()
# Gui.Selection.addSelection('Unnamed','Body','Sketch.Edge32',-14.7907,39.3065,0.008,False)
# Gui.Selection.removeSelection('Unnamed','Body','Sketch.Edge32')
# Gui.runCommand('Sketcher_ToggleConstruction',0)
# Gui.Selection.addSelection('Unnamed','Body','Sketch.Edge32',-19.3327,39.1906,0.008,False)
### Begin command Sketcher_ToggleConstruction
App.getDocument('Unnamed').getObject('Sketch').toggleConstruction(31) 
### End command Sketcher_ToggleConstruction
# Gui.Selection.clearSelection()
# Gui.Selection.addSelection('Unnamed','Body','Sketch.Edge31',-20.4691,39.4496,0.008,False)
### Begin command Sketcher_ToggleConstruction
App.getDocument('Unnamed').getObject('Sketch').toggleConstruction(30) 
### End command Sketcher_ToggleConstruction
# Gui.Selection.clearSelection()
# Gui.runCommand('Sketcher_CreateLine',0)
ActiveSketch = App.getDocument('Unnamed').getObject('Sketch')

lastGeoId = len(ActiveSketch.Geometry)

constrGeoList = []
constrGeoList.append(Part.LineSegment(App.Vector(-17.024558, 41.249929, 0.000000),App.Vector(-16.947149, 32.750329, 0.000000)))
App.getDocument('Unnamed').getObject('Sketch').addGeometry(constrGeoList,True)
del constrGeoList

constraintList = []
constraintList = []
constraintList.append(Sketcher.Constraint('PointOnObject', 35, 1, 30))
constraintList.append(Sketcher.Constraint('PointOnObject', 35, 2, 30))
constraintList.append(Sketcher.Constraint('Vertical', 35))
App.getDocument('Unnamed').getObject('Sketch').addConstraint(constraintList)
del constraintList

# Gui.Selection.addSelection('Unnamed','Body','Sketch.Edge36',-16.9471,36.6552,0.008,False)
# Gui.Selection.addSelection('Unnamed','Body','Sketch.Vertex60',-17,37,0.014,False)
### Begin command Sketcher_ConstrainCoincidentUnified
App.getDocument('Unnamed').getObject('Sketch').addConstraint(Sketcher.Constraint('PointOnObject',30,3,35))
### End command Sketcher_ConstrainCoincidentUnified
# Gui.Selection.clearSelection()
# Gui.runCommand('Sketcher_CreateLine',0)
ActiveSketch = App.getDocument('Unnamed').getObject('Sketch')

lastGeoId = len(ActiveSketch.Geometry)

constrGeoList = []
constrGeoList.append(Part.LineSegment(App.Vector(-21.242164, 36.742045, 0.000000),App.Vector(-12.761668, 36.685288, 0.000000)))
App.getDocument('Unnamed').getObject('Sketch').addGeometry(constrGeoList,True)
del constrGeoList

constraintList = []
constraintList = []
constraintList.append(Sketcher.Constraint('PointOnObject', 36, 1, 30))
constraintList.append(Sketcher.Constraint('PointOnObject', 36, 2, 30))
constraintList.append(Sketcher.Constraint('Horizontal', 36))
App.getDocument('Unnamed').getObject('Sketch').addConstraint(constraintList)
del constraintList

# Gui.Selection.addSelection('Unnamed','Body','Sketch.Vertex60',-17,37,0.014,False)
# Gui.Selection.addSelection('Unnamed','Body','Sketch.Edge37',-17.1311,36.742,0.008,False)
### Begin command Sketcher_ConstrainCoincidentUnified
App.getDocument('Unnamed').getObject('Sketch').addConstraint(Sketcher.Constraint('PointOnObject',30,3,36))
### End command Sketcher_ConstrainCoincidentUnified
# Gui.Selection.clearSelection()
# Gui.runCommand('Sketcher_CompCreateArc',0)
ActiveSketch = App.getDocument('Unnamed').getObject('Sketch')

lastGeoId = len(ActiveSketch.Geometry)

constrGeoList = []
constrGeoList.append(Part.ArcOfCircle(Part.Circle(App.Vector(-17.000000, 32.750000, 0.000000), App.Vector(0.000000, 0.000000, 1.000000), 1.187877), 0.084556, 3.001383))
App.getDocument('Unnamed').getObject('Sketch').addGeometry(constrGeoList,True)
del constrGeoList

constraintList = []
constraintList = []
constraintList.append(Sketcher.Constraint('Coincident', 37, 3, 35, 2))
constraintList.append(Sketcher.Constraint('PointOnObject', 37, 2, 30))
constraintList.append(Sketcher.Constraint('PointOnObject', 37, 1, 30))
App.getDocument('Unnamed').getObject('Sketch').addConstraint(constraintList)
del constraintList

# Gui.Selection.addSelection('Unnamed','Body','Sketch.Edge38',-16.0539,33.4777,0.008,False)
### Begin command Sketcher_ToggleConstruction
App.getDocument('Unnamed').getObject('Sketch').toggleConstruction(37) 
### End command Sketcher_ToggleConstruction
# Gui.Selection.clearSelection()
# Gui.runCommand('Sketcher_CompDimensionTools',0)
App.getDocument('Unnamed').getObject('Sketch').addConstraint(Sketcher.Constraint('Radius',37,1.193603)) 
# Gui.Selection.addSelection('Unnamed','Body','Sketch.Edge38',-16.1798,33.6172,0)
App.getDocument('Unnamed').Sketch.setExpression('Constraints[110]', u'<<Spreadsheet>>.gear_tooth_rad')
# Gui.Selection.clearSelection()
# Gui.Selection.addSelection('Unnamed','Body','Sketch.Edge38',-16.5293,34.8987,0.008,False)
### Begin command Std_Delete
App.getDocument('Unnamed').getObject('Sketch').delGeometries([37])
App.getDocument('Unnamed').recompute()
### End command Std_Delete
# Gui.Selection.clearSelection()
# Gui.runCommand('Sketcher_CompDimensionTools',0)
App.getDocument('Unnamed').getObject('Sketch').addConstraint(Sketcher.Constraint('Diameter',31,6.400000)) 
# Gui.Selection.addSelection('Unnamed','Body','Sketch.Edge32',-19.577,35.1029,0)
App.getDocument('Unnamed').getObject('Sketch').addConstraint(Sketcher.Constraint('Distance',31,30,1.050000))
# Gui.Selection.addSelection('Unnamed','Body','Sketch.Edge31',-20.5999,34.741,0)
App.getDocument('Unnamed').getObject('Sketch').addConstraint(Sketcher.Constraint('Diameter',31,6.400000)) 
# Gui.Selection.removeSelection('Unnamed','Body','Sketch.Edge31')
# Gui.Selection.clearSelection()
# Gui.runCommand('Sketcher_CompCreateConic',0)
ActiveSketch = App.getDocument('Unnamed').getObject('Sketch')

lastGeoId = len(ActiveSketch.Geometry)

constrGeoList = []
constrGeoList.append(Part.Circle(App.Vector(-17.000000, 32.750000, 0.000000), App.Vector(0.000000, 0.000000, 1.000000), 1.063645))
App.getDocument('Unnamed').getObject('Sketch').addGeometry(constrGeoList,True)
del constrGeoList

constraintList = []
App.getDocument('Unnamed').getObject('Sketch').addConstraint(Sketcher.Constraint('Coincident', 37, 3, 35, 2))


# Gui.runCommand('Sketcher_Dimension',0)
App.getDocument('Unnamed').getObject('Sketch').addConstraint(Sketcher.Constraint('Diameter',37,2.127290)) 
# Gui.Selection.addSelection('Unnamed','Body','Sketch.Edge38',-15.9676,32.494,0)
# Gui.Selection.clearSelection()
# Gui.Selection.addSelection('Unnamed','Body','Sketch.Edge38',-16.0679,33.2624,0.008,False)
# Gui.Selection.clearSelection()
# Gui.Selection.addSelection('Unnamed','Body','Sketch.Edge38',-17.6512,33.589,0.008,False)
### Begin command Std_Delete
App.getDocument('Unnamed').getObject('Sketch').delGeometries([37])
App.getDocument('Unnamed').recompute()
### End command Std_Delete
# Gui.Selection.clearSelection()
# Gui.runCommand('Sketcher_CompCreateArc',0)
# Gui.runCommand('Sketcher_CreatePoint',0)
App.getDocument('Unnamed').getObject('Sketch').addGeometry(Part.Point(App.Vector(-17.000000,33.874573,0)), True)
App.getDocument('Unnamed').getObject('Sketch').addConstraint(Sketcher.Constraint('PointOnObject',37,1,35)) 
# Gui.Selection.addSelection('Unnamed','Body','Sketch.Vertex73',-17,33.8746,0.014,False)
# Gui.Selection.addSelection('Unnamed','Body','Sketch.Edge32',-16.9298,33.8063,0.008,False)
### Begin command Sketcher_ConstrainCoincidentUnified
App.getDocument('Unnamed').getObject('Sketch').addConstraint(Sketcher.Constraint('PointOnObject',37,1,31))
### End command Sketcher_ConstrainCoincidentUnified
# Gui.Selection.clearSelection()
# Gui.runCommand('Sketcher_CompDimensionTools',0)
App.getDocument('Unnamed').getObject('Sketch').addConstraint(Sketcher.Constraint('Distance',37,1,-1,1,37.834376)) 
# Gui.Selection.addSelection('Unnamed','Body','Sketch.Vertex73',-17,33.8,0)
App.getDocument('Unnamed').getObject('Sketch').addConstraint(Sketcher.Constraint('DistanceY',-1,1,37,1,33.800000)) 
App.getDocument('Unnamed').getObject('Sketch').addConstraint(Sketcher.Constraint('Distance',37,1,-1,1,37.834376)) 
App.getDocument('Unnamed').getObject('Sketch').addConstraint(Sketcher.Constraint('Distance',37,1,35,2,1.050000)) 
# Gui.Selection.addSelection('Unnamed','Body','Sketch.Vertex70',-17,32.75,0)
App.getDocument('Unnamed').getObject('Sketch').addConstraint(Sketcher.Constraint('DistanceY',35,2,37,1,1.050000)) 
# Gui.Selection.clearSelection()
# Gui.Selection.addSelection('Unnamed','Body','Sketch.Constraint85',4.69092,38.6064,0.009,False)
# Gui.Selection.removeSelection('Unnamed','Body','Sketch.Constraint85')
App.getDocument('Unnamed').Sketch.setExpression('Constraints[84]', u'<<Spreadsheet>>.gear_inner_rad * 2')
# Gui.Selection.addSelection('Unnamed','Body','Sketch.Constraint86',3.36258,39.6551,0.009,False)
# Gui.Selection.removeSelection('Unnamed','Body','Sketch.Constraint86')
App.getDocument('Unnamed').Sketch.setExpression('Constraints[85]', u'<<Spreadsheet>>.gear_outer_rad * 2')
# Gui.runCommand('Sketcher_CompCreateArc',0)
# Gui.runCommand('Sketcher_ToggleConstruction',0)
# Gui.runCommand('Sketcher_Create3PointArc',0)
# Gui.runCommand('Sketcher_CompCreateArc',1)
# Gui.runCommand('Sketcher_CreateArc',0)
# Gui.runCommand('Sketcher_CompCreateArc',0)
ActiveSketch = App.getDocument('Unnamed').getObject('Sketch')

lastGeoId = len(ActiveSketch.Geometry)

geoList = []
geoList.append(Part.ArcOfCircle(Part.Circle(App.Vector(-17.000000, 28.500000, 0.000000), App.Vector(0.000000, 0.000000, 1.000000), 2.100000), 0.128551, 1.570796))
App.getDocument('Unnamed').getObject('Sketch').addGeometry(geoList,False)
del geoList

constraintList = []
constraintList = []
constraintList.append(Sketcher.Constraint('Coincident', 38, 3, 35, 2))
constraintList.append(Sketcher.Constraint('Coincident', 38, 2, 37, 1))
constraintList.append(Sketcher.Constraint('PointOnObject', 38, 1, 30))
App.getDocument('Unnamed').getObject('Sketch').addConstraint(constraintList)
del constraintList

# Gui.Selection.addSelection('Unnamed','Body','Sketch.Edge39',-15.4752,29.9438,0.008,False)
### Begin command Std_Delete
App.getDocument('Unnamed').getObject('Sketch').delGeometries([38])
App.getDocument('Unnamed').recompute()
### End command Std_Delete
# Gui.Selection.clearSelection()
# Gui.runCommand('Sketcher_CompCreateArc',0)
ActiveSketch = App.getDocument('Unnamed').getObject('Sketch')

lastGeoId = len(ActiveSketch.Geometry)

geoList = []
geoList.append(Part.ArcOfCircle(Part.Circle(App.Vector(-16.970857, 28.500050, 0.000000), App.Vector(0.000000, 0.000000, 1.000000), 2.211060), 0.082645, 3.014589))
App.getDocument('Unnamed').getObject('Sketch').addGeometry(geoList,False)
del geoList

constraintList = []
constraintList = []
constraintList.append(Sketcher.Constraint('PointOnObject', 38, 3, 30))
constraintList.append(Sketcher.Constraint('PointOnObject', 38, 2, 30))
constraintList.append(Sketcher.Constraint('PointOnObject', 38, 1, 30))
App.getDocument('Unnamed').getObject('Sketch').addConstraint(constraintList)
del constraintList

# Gui.runCommand('Sketcher_CompDimensionTools',0)
App.getDocument('Unnamed').getObject('Sketch').addConstraint(Sketcher.Constraint('Radius',38,2.216974)) 
# Gui.Selection.addSelection('Unnamed','Body','Sketch.Edge39',-14.9604,29.4471,0)
App.getDocument('Unnamed').Sketch.setExpression('Constraints[112]', u'<<Spreadsheet>>.gear_tooth_rad')
# Gui.Selection.clearSelection()
App.getDocument('Unnamed').getObject('Sketch').movePoint(38,2,App.Vector(-19.429592,28.828663,0),0)
# Gui.Selection.addSelection('Unnamed','Body','Sketch.Vertex70',-17,28.5,0.014,False)
# Gui.runCommand('Sketcher_ConstrainCoincidentUnified',0)
# Gui.Selection.clearSelection()
# Gui.Selection.addSelection('Unnamed','Body','Sketch.Vertex76',-17.2503,28.5037,0.014,False)
# Gui.Selection.addSelection('Unnamed','Body','Sketch.Vertex70',-17,28.5,0.014,False)
### Begin command Sketcher_ConstrainCoincidentUnified
App.getDocument('Unnamed').getObject('Sketch').addConstraint(Sketcher.Constraint('Coincident',38,3,35,2))
### End command Sketcher_ConstrainCoincidentUnified
# Gui.Selection.clearSelection()
# Gui.runCommand('Std_Undo',0)
# Gui.Selection.addSelection('Unnamed','Body','Sketch.Edge39',-17.9348,30.5945,0.008,False)
### Begin command Std_Delete
App.getDocument('Unnamed').getObject('Sketch').delGeometries([38])
App.getDocument('Unnamed').recompute()
### End command Std_Delete
# Gui.Selection.clearSelection()
# Gui.runCommand('Sketcher_CompCreateArc',0)
ActiveSketch = App.getDocument('Unnamed').getObject('Sketch')

lastGeoId = len(ActiveSketch.Geometry)

geoList = []
geoList.append(Part.ArcOfCircle(Part.Circle(App.Vector(-17.000000, 28.500000, 0.000000), App.Vector(0.000000, 0.000000, 1.000000), 2.419294), 0.142796, 2.894462))
App.getDocument('Unnamed').getObject('Sketch').addGeometry(geoList,False)
del geoList

constraintList = []
constraintList = []
constraintList.append(Sketcher.Constraint('Coincident', 38, 3, 35, 2))
constraintList.append(Sketcher.Constraint('PointOnObject', 38, 1, 30))
constraintList.append(Sketcher.Constraint('PointOnObject', 38, 2, 30))
App.getDocument('Unnamed').getObject('Sketch').addConstraint(constraintList)
del constraintList

App.getDocument('Unnamed').getObject('Sketch').movePoint(38,0,App.Vector(-16.322218,30.456148,0),0)
App.getDocument('Unnamed').getObject('Sketch').movePoint(38,0,App.Vector(-15.732615,30.371920,0),0)
# Gui.runCommand('Sketcher_CompDimensionTools',0)
App.getDocument('Unnamed').getObject('Sketch').addConstraint(Sketcher.Constraint('Radius',38,2.260608)) 
# Gui.Selection.addSelection('Unnamed','Body','Sketch.Edge39',-15.1136,29.7457,0)
App.getDocument('Unnamed').Sketch.setExpression('Constraints[112]', u'<<Spreadsheet>>.gear_tooth_rad')
# Gui.Selection.clearSelection()
# Gui.Selection.addSelection('Unnamed','Body','Sketch.Edge39',-15.9092,30.4105,0.008,False)
# Gui.runCommand('Sketcher_Symmetry',0)
# Gui.Selection.clearSelection()
App.ActiveDocument.recompute()
# Gui.Selection.addSelection('Unnamed','Body','Sketch.')
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_ConstrainBlock',0)
# Gui.Selection.addSelection('Unnamed','Body','Sketch.Edge40',-15.9654,43.5585,0)
App.getDocument('Unnamed').getObject('Sketch').addConstraint(Sketcher.Constraint('Block',39))
# Gui.Selection.clearSelection()
# Gui.runCommand('Sketcher_CreateLine',0)
# Gui.runCommand('Sketcher_ToggleConstruction',0)
ActiveSketch = App.getDocument('Unnamed').getObject('Sketch')

lastGeoId = len(ActiveSketch.Geometry)

constrGeoList = []
constrGeoList.append(Part.LineSegment(App.Vector(-23.450233, 42.535747, 0.000000),App.Vector(-10.250237, 31.833696, 0.000000)))
App.getDocument('Unnamed').getObject('Sketch').addGeometry(constrGeoList,True)
del constrGeoList

constraintList = []
constraintList = []
constraintList.append(Sketcher.Constraint('PointOnObject', 40, 1, 30))
constraintList.append(Sketcher.Constraint('PointOnObject', 40, 2, 30))
App.getDocument('Unnamed').getObject('Sketch').addConstraint(constraintList)
del constraintList

# Gui.Selection.addSelection('Unnamed','Body','Sketch.Vertex60',-17,37,0.014,False)
# Gui.Selection.clearSelection()
# Gui.Selection.addSelection('Unnamed','Body','Sketch.Edge41',-16.1988,36.6566,0.008,False)
# Gui.runCommand('Sketcher_ConstrainCoincidentUnified',0)
# Gui.Selection.addSelection('Unnamed','Body','Sketch.Vertex60',-17,37,0.014,False)
### Begin command Sketcher_ConstrainCoincidentUnified
App.getDocument('Unnamed').getObject('Sketch').addConstraint(Sketcher.Constraint('PointOnObject',30,3,40))
### End command Sketcher_ConstrainCoincidentUnified
# Gui.Selection.clearSelection()
# Gui.Selection.addSelection('Unnamed','Body','Sketch.Edge40',-18.7533,44.1711,0.008,False)
# Gui.runCommand('Sketcher_Symmetry',0)
# Gui.Selection.clearSelection()
# Gui.runCommand('Std_Undo',0)
App.ActiveDocument.recompute()
# Gui.Selection.addSelection('Unnamed','Body','Sketch.')
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompDimensionTools',0)
App.getDocument('Unnamed').getObject('Sketch').addConstraint(Sketcher.Constraint('Distance',40,1,40,2,17.000000)) 
# Gui.Selection.addSelection('Unnamed','Body','Sketch.Edge41',-20.1956,39.4572,0)
App.getDocument('Unnamed').getObject('Sketch').addConstraint(Sketcher.Constraint('Angle',36,2,40,1,2.486092)) 
# Gui.Selection.addSelection('Unnamed','Body','Sketch.Edge37',-21.4913,37,0)
App.getDocument('Unnamed').getObject('Sketch').setDatum(118,App.Units.Quantity('45.000000 deg'))
# Gui.Selection.clearSelection()
# Gui.runCommand('Sketcher_ToggleConstruction',0)
# Gui.Selection.addSelection('Unnamed','Body','Sketch.Edge40',-18.5011,43.8919,0.008,False)
# Gui.runCommand('Sketcher_Symmetry',0)
# Gui.Selection.clearSelection()
# Gui.Selection.addSelection('Unnamed','Body','Sketch.Edge42',-24.0472,38.6512,0.008,False)
# Gui.runCommand('Sketcher_Symmetry',0)
# Gui.Selection.clearSelection()
# Gui.Selection.addSelection('Unnamed','Body','Sketch.Edge1',-18.8782,38.8782,0.006,False)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.runCommand('Std_Undo',0)
# Gui.Selection.clearSelection()
# Gui.runCommand('Sketcher_CompCreateConic',0)
# Gui.runCommand('Sketcher_CompCreateArc',0)
ActiveSketch = App.getDocument('Unnamed').getObject('Sketch')

lastGeoId = len(ActiveSketch.Geometry)

geoList = []
geoList.append(Part.ArcOfCircle(Part.Circle(App.Vector(-12.453785, 29.817944, 0.000000), App.Vector(0.000000, 0.000000, 1.000000), 1.769337), 0.685277, 3.601654))
App.getDocument('Unnamed').getObject('Sketch').addGeometry(geoList,False)
del geoList

constraintList = []
constraintList = []
constraintList.append(Sketcher.Constraint('PointOnObject', 40, 3, 30))
constraintList.append(Sketcher.Constraint('PointOnObject', 40, 2, 30))
constraintList.append(Sketcher.Constraint('PointOnObject', 40, 1, 30))
App.getDocument('Unnamed').getObject('Sketch').addConstraint(constraintList)
del constraintList

ActiveSketch = App.getDocument('Unnamed').getObject('Sketch')

lastGeoId = len(ActiveSketch.Geometry)

geoList = []
geoList.append(Part.ArcOfCircle(Part.Circle(App.Vector(-9.327553, 33.341646, 0.000000), App.Vector(0.000000, 0.000000, 1.000000), 1.479880), 1.200809, 4.180297))
App.getDocument('Unnamed').getObject('Sketch').addGeometry(geoList,False)
del geoList

constraintList = []
constraintList = []
constraintList.append(Sketcher.Constraint('PointOnObject', 41, 3, 30))
constraintList.append(Sketcher.Constraint('PointOnObject', 41, 2, 30))
constraintList.append(Sketcher.Constraint('PointOnObject', 41, 1, 30))
App.getDocument('Unnamed').getObject('Sketch').addConstraint(constraintList)
del constraintList

# Gui.Selection.addSelection('Unnamed','Body','Sketch.Edge39',-15.4334,30.0436,0.008,False)
# Gui.Selection.addSelection('Unnamed','Body','Sketch.Edge41',-13.4714,31.2499,0.008,False)
# Gui.Selection.addSelection('Unnamed','Body','Sketch.Edge42',-10.7116,32.8223,0.008,False)
### Begin command Sketcher_ConstrainEqual
App.getDocument('Unnamed').getObject('Sketch').addConstraint(Sketcher.Constraint('Equal',38,40))
App.getDocument('Unnamed').getObject('Sketch').addConstraint(Sketcher.Constraint('Equal',40,41))
### End command Sketcher_ConstrainEqual
# Gui.Selection.clearSelection()
App.getDocument('Unnamed').getObject('Sketch').movePoint(41,1,App.Vector(-8.516615,36.468792,0),0)
App.getDocument('Unnamed').getObject('Sketch').movePoint(40,1,App.Vector(-10.255129,31.827311,0),0)
App.getDocument('Unnamed').getObject('Sketch').movePoint(40,2,App.Vector(-13.890663,29.016191,0),0)
# Gui.runCommand('Sketcher_CreateLine',0)
ActiveSketch = App.getDocument('Unnamed').getObject('Sketch')

lastGeoId = len(ActiveSketch.Geometry)

geoList = []
geoList.append(Part.LineSegment(App.Vector(-14.818500, 28.784706, 0.000000),App.Vector(-13.915290, 29.079485, 0.000000)))
App.getDocument('Unnamed').getObject('Sketch').addGeometry(geoList,False)
del geoList

constraintList = []
constraintList = []
constraintList.append(Sketcher.Constraint('Coincident', 42, 1, 38, 1))
constraintList.append(Sketcher.Constraint('Coincident', 42, 2, 40, 2))
constraintList.append(Sketcher.Constraint('Tangent', 42, 30))
App.getDocument('Unnamed').getObject('Sketch').addConstraint(constraintList)
del constraintList

# Gui.runCommand('Std_Undo',0)
# Gui.runCommand('Std_Undo',0)
# Gui.runCommand('Sketcher_CompCurveEdition',0)
App.getDocument('Unnamed').getObject('Sketch').trim(30,App.Vector(-13.207511,29.463623,0))
App.getDocument('Unnamed').getObject('Sketch').trim(30,App.Vector(-9.491229,33.179905,0))
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(42,App.Vector(-17.764891,28.551548,0))
App.getDocument('Unnamed').getObject('Sketch').trim(43,App.Vector(-16.139345,28.509325,0))
# Gui.Selection.addSelection('Unnamed','Body','Sketch.Edge44',-14.3809,28.9136,0.008,False)
# Gui.Selection.addSelection('Unnamed','Body','Sketch.Edge31',-10.2573,31.8245,0.008,False)
### Begin command Sketcher_ConstrainEqual
App.getDocument('Unnamed').getObject('Sketch').addConstraint(Sketcher.Constraint('Equal',43,30))
### End command Sketcher_ConstrainEqual
# Gui.Selection.clearSelection()
### Begin command Std_Delete
App.getDocument('Unnamed').getObject('Sketch').delConstraint(128)
App.getDocument('Unnamed').recompute()
### End command Std_Delete
# Gui.Selection.clearSelection()
App.getDocument('Unnamed').getObject('Sketch').movePoint(42,0,App.Vector(-22.197475,41.484035,0),0)
App.getDocument('Unnamed').getObject('Sketch').movePoint(40,2,App.Vector(-14.318156,28.934164,0),0)
App.getDocument('Unnamed').getObject('Sketch').movePoint(30,1,App.Vector(-10.404709,31.637897,0),0)
# Gui.Selection.addSelection('Unnamed','Body','Sketch.Edge41',-14.0982,30.7921,0.008,False)
# Gui.Selection.clearSelection()
# Gui.Selection.addSelection('Unnamed','Body','Sketch.Edge41',-14.2013,30.1687,0.008,False)
# Gui.Selection.addSelection('Unnamed','Body','Sketch.Edge42',-10.6781,32.9643,0.008,False)
# Gui.runCommand('Sketcher_Symmetry',0)
# Gui.Selection.clearSelection()
App.ActiveDocument.recompute()
# Gui.Selection.addSelection('Unnamed','Body','Sketch.')
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(42,App.Vector(-11.256852,43.241379,0))
App.getDocument('Unnamed').getObject('Sketch').trim(42,App.Vector(-9.218118,40.587173,0))
# Gui.Selection.addSelection('Unnamed','Body','Sketch.Constraint125',-14.2052,28.2331,0.0179977,False)
# Gui.Selection.clearSelection()
# Gui.Selection.addSelection('Unnamed','Body','Sketch.Constraint121',-9.56078,31.5687,0.00900269,False)
# Gui.Selection.removeSelection('Unnamed','Body','Sketch.Constraint121')
App.getDocument('Unnamed').getObject('Sketch').movePoint(40,0,App.Vector(-13.896083,29.293001,0),0)
# Gui.Selection.addSelection('Unnamed','Body','Sketch.Edge44',-14.2479,28.9579,0.008,False)
# Gui.Selection.addSelection('Unnamed','Body','Sketch.Edge31',-10.1542,31.9616,0.008,False)
# Gui.Selection.addSelection('Unnamed','Body','Sketch.Edge43',-8.50215,37.1914,0.008,False)
### Begin command Sketcher_ConstrainEqual
App.getDocument('Unnamed').getObject('Sketch').addConstraint(Sketcher.Constraint('Equal',43,30))
App.getDocument('Unnamed').getObject('Sketch').addConstraint(Sketcher.Constraint('Equal',30,42))
### End command Sketcher_ConstrainEqual
# Gui.Selection.clearSelection()
### Begin command Std_Delete
App.getDocument('Unnamed').getObject('Sketch').delConstraint(120)
App.getDocument('Unnamed').recompute()
### End command Std_Delete
# Gui.Selection.clearSelection()
### Begin command Std_Delete
App.getDocument('Unnamed').getObject('Sketch').delConstraint(137)
App.getDocument('Unnamed').recompute()
### End command Std_Delete
# Gui.Selection.clearSelection()
# Gui.runCommand('Sketcher_CompCurveEdition',0)
App.getDocument('Unnamed').getObject('Sketch').trim(46,App.Vector(-17.677740,45.497410,0))
App.getDocument('Unnamed').getObject('Sketch').trim(46,App.Vector(-16.323502,45.465916,0))
# Gui.Selection.addSelection('Unnamed','Body','Sketch.Edge45',-11.9898,41.6752,0.008,False)
# Gui.Selection.addSelection('Unnamed','Body','Sketch.Edge46',-10.9394,40.6023,0.008,False)
# Gui.Selection.addSelection('Unnamed','Body','Sketch.Edge42',-10.1002,36.1767,0.008,False)
# Gui.Selection.addSelection('Unnamed','Body','Sketch.Edge41',-11.6634,32.3925,0.008,False)
# Gui.runCommand('Sketcher_Symmetry',0)
# Gui.Selection.clearSelection()
App.ActiveDocument.recompute()
# Gui.Selection.addSelection('Unnamed','Body','Sketch.')
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_ConstrainBlock',0)
# Gui.Selection.addSelection('Unnamed','Body','Sketch.Edge45',-14.0217,43.0034,0)
App.getDocument('Unnamed').getObject('Sketch').addConstraint(Sketcher.Constraint('Block',44))
# Gui.Selection.clearSelection()
# Gui.Selection.addSelection('Unnamed','Body','Sketch.Edge46',-10.7418,40.9489,0)
App.getDocument('Unnamed').getObject('Sketch').addConstraint(Sketcher.Constraint('Block',45))
# Gui.Selection.clearSelection()
# Gui.Selection.addSelection('Unnamed','Body','Sketch.Edge41',-11.782,32.4018,0)
App.getDocument('Unnamed').getObject('Sketch').addConstraint(Sketcher.Constraint('Block',40))
# Gui.Selection.clearSelection()
# Gui.Selection.addSelection('Unnamed','Body','Sketch.Edge42',-10.8933,33.3026,0)
App.getDocument('Unnamed').getObject('Sketch').addConstraint(Sketcher.Constraint('Block',41))
# Gui.Selection.clearSelection()
# Gui.Selection.addSelection('Unnamed','Body','Sketch.Edge53',-22.1054,32.4046,0)
App.getDocument('Unnamed').getObject('Sketch').addConstraint(Sketcher.Constraint('Block',52))
# Gui.Selection.clearSelection()
# Gui.Selection.addSelection('Unnamed','Body','Sketch.Edge52',-23.2529,33.0588,0)
App.getDocument('Unnamed').getObject('Sketch').addConstraint(Sketcher.Constraint('Block',51))
# Gui.Selection.clearSelection()
# Gui.Selection.addSelection('Unnamed','Body','Sketch.Edge51',-24.3654,37.6042,0)
App.getDocument('Unnamed').getObject('Sketch').addConstraint(Sketcher.Constraint('Block',50))
# Gui.Selection.clearSelection()
# Gui.Selection.addSelection('Unnamed','Body','Sketch.Edge50',-22.3698,41.7068,0)
App.getDocument('Unnamed').getObject('Sketch').addConstraint(Sketcher.Constraint('Block',49))
# Gui.Selection.clearSelection()
App.getDocument('Unnamed').getObject('Sketch').movePoint(48,0,App.Vector(-20.042206,28.863117,0),0)
App.getDocument('Unnamed').getObject('Sketch').movePoint(52,1,App.Vector(-20.376556,28.734520,0),0)
App.getDocument('Unnamed').getObject('Sketch').movePoint(45,3,App.Vector(-8.312260,37.571213,0),0)
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCurveEdition',0)
App.getDocument('Unnamed').getObject('Sketch').trim(48,App.Vector(-23.364513,42.624813,0))
App.getDocument('Unnamed').getObject('Sketch').trim(53,App.Vector(-24.715614,40.619270,0))
App.getDocument('Unnamed').getObject('Sketch').trim(54,App.Vector(-25.327833,35.109306,0))
App.getDocument('Unnamed').getObject('Sketch').trim(55,App.Vector(-22.731182,30.739332,0))
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(39,3,App.Vector(-16.882820,42.991432,0),0)
App.getDocument('Unnamed').getObject('Sketch').movePoint(30,3,App.Vector(-16.568684,36.645878,0),0)
App.getDocument('Unnamed').getObject('Sketch').movePoint(50,0,App.Vector(-21.877590,38.028080,0),0)
App.getDocument('Unnamed').getObject('Sketch').movePoint(54,0,App.Vector(-26.212671,37.179909,0),0)
App.getDocument('Unnamed').getObject('Sketch').movePoint(42,0,App.Vector(-8.244067,36.645878,0),0)
App.getDocument('Unnamed').getObject('Sketch').movePoint(47,0,App.Vector(-9.783338,40.980961,0),0)
App.getDocument('Unnamed').getObject('Sketch').movePoint(40,2,App.Vector(-12.547738,29.169432,0),0)
# Gui.Selection.addSelection('Unnamed','Body','Sketch.Vertex60',0,0,0,False)
# Gui.Selection.addSelection('Unnamed','Body','Sketch.Edge31',0,0,0,False)
# Gui.Selection.addSelection('Unnamed','Body','Sketch.Vertex82',0,0,0,False)
# Gui.Selection.addSelection('Unnamed','Body','Sketch.Edge41',0,0,0,False)
# Gui.Selection.addSelection('Unnamed','Body','Sketch.Edge32',-11.7893,33.2902,0.008,False)
# Gui.Selection.removeSelection('Unnamed','Body','Sketch.Edge31')
# Gui.Selection.clearSelection()
# Gui.Selection.addSelection('Unnamed','Body','Sketch.Edge32',-11.7789,33.3066,0.008,False)
### Begin command Std_Delete
App.getDocument('Unnamed').getObject('Sketch').delGeometries([31])
App.getDocument('Unnamed').recompute()
### End command Std_Delete
# Gui.Selection.clearSelection()
# Gui.runCommand('Std_Undo',0)
App.getDocument('Unnamed').getObject('Sketch').movePoint(52,0,App.Vector(-19.178516,32.142487,0),0)
App.getDocument('Unnamed').getObject('Sketch').movePoint(52,0,App.Vector(-18.432657,29.621994,0),0)
App.getDocument('Unnamed').getObject('Sketch').movePoint(38,0,App.Vector(-18.972763,31.216591,0),0)
App.getDocument('Unnamed').getObject('Sketch').movePoint(56,0,App.Vector(-19.692904,28.490343,0),0)
App.getDocument('Unnamed').getObject('Sketch').movePoint(52,1,App.Vector(-19.049921,29.261923,0),0)
App.getDocument('Unnamed').getObject('Sketch').movePoint(38,1,App.Vector(-15.114865,28.747536,0),0)
# Gui.Selection.addSelection('Unnamed','Body','Sketch.Edge42',0,0,0,False)
# Gui.Selection.clearSelection()
App.getDocument('Unnamed').getObject('Sketch').movePoint(31,0,App.Vector(-20.945951,41.399483,0),0)
App.getDocument('Unnamed').getObject('Sketch').movePoint(54,0,App.Vector(-26.038794,36.667164,0),0)
App.getDocument('Unnamed').getObject('Sketch').movePoint(51,2,App.Vector(-25.338634,36.846935,0),0)
App.getDocument('Unnamed').getObject('Sketch').movePoint(50,1,App.Vector(-25.433250,37.197014,0),0)
App.getDocument('Unnamed').getObject('Sketch').movePoint(42,0,App.Vector(-9.570370,36.616718,0),0)
App.getDocument('Unnamed').getObject('Sketch').movePoint(30,0,App.Vector(-11.706500,32.752838,0),0)
# Gui.Selection.addSelection('Unnamed','Body','Sketch.Edge44',-14.4909,28.8788,0.008,False)
# Gui.Selection.clearSelection()
App.getDocument('Unnamed').getObject('Sketch').movePoint(56,0,App.Vector(-20.197041,27.903643,0),0)
App.getDocument('Unnamed').getObject('Sketch').movePoint(56,0,App.Vector(-14.813785,27.623993,0),0)
App.getDocument('Unnamed').getObject('Sketch').movePoint(55,0,App.Vector(-24.835943,31.080414,0),0)
App.getDocument('Unnamed').getObject('Sketch').movePoint(54,0,App.Vector(-27.286209,36.986187,0),0)
# Gui.runCommand('Sketcher_ConstrainBlock',0)
# Gui.Selection.addSelection('Unnamed','Body','Sketch.Edge49',-19.6278,45.0836,0)
App.getDocument('Unnamed').getObject('Sketch').addConstraint(Sketcher.Constraint('Block',48))
# Gui.Selection.clearSelection()
# Gui.runCommand('Std_Undo',0)
# Gui.Selection.addSelection('Unnamed','Body','Sketch.Edge47',-14.1562,45.0102,0)
App.getDocument('Unnamed').getObject('Sketch').addConstraint(Sketcher.Constraint('Block',46))
# Gui.Selection.clearSelection()
# Gui.Selection.addSelection('Unnamed','Body','Sketch.Edge48',-10.0264,41.8599,0)
App.getDocument('Unnamed').getObject('Sketch').addConstraint(Sketcher.Constraint('Block',47))
# Gui.Selection.clearSelection()
# Gui.Selection.addSelection('Unnamed','Body','Sketch.Edge56',-23.897,32.0319,0)
App.getDocument('Unnamed').getObject('Sketch').addConstraint(Sketcher.Constraint('Block',55))
# Gui.Selection.clearSelection()
# Gui.Selection.addSelection('Unnamed','Body','Sketch.Edge55',-25.4988,37.1445,0)
App.getDocument('Unnamed').getObject('Sketch').addConstraint(Sketcher.Constraint('Block',54))
# Gui.Selection.clearSelection()
# Gui.Selection.addSelection('Unnamed','Body','Sketch.Edge54',-23.8575,42.0224,0)
App.getDocument('Unnamed').getObject('Sketch').addConstraint(Sketcher.Constraint('Block',53))
# Gui.Selection.clearSelection()
# Gui.Selection.addSelection('Unnamed','Body','Sketch.Edge49',-19.4308,45.145,0)
App.getDocument('Unnamed').getObject('Sketch').addConstraint(Sketcher.Constraint('Block',48))
# Gui.Selection.clearSelection()
# Gui.Selection.addSelection('Unnamed','Body','Sketch.Edge31',-10.1807,31.9259,0)
App.getDocument('Unnamed').getObject('Sketch').addConstraint(Sketcher.Constraint('Block',30))
# Gui.Selection.clearSelection()
# Gui.Selection.addSelection('Unnamed','Body','Sketch.Edge44',-14.3084,28.9374,0)
App.getDocument('Unnamed').getObject('Sketch').addConstraint(Sketcher.Constraint('Block',43))
# Gui.Selection.clearSelection()
# Gui.Selection.addSelection('Unnamed','Body','Sketch.Edge57',-19.8403,28.9886,0)
App.getDocument('Unnamed').getObject('Sketch').addConstraint(Sketcher.Constraint('Block',56))
# Gui.Selection.clearSelection()
# Gui.Selection.addSelection('Unnamed','Body','Sketch.Edge43',-8.50764,36.6397,0)
App.getDocument('Unnamed').getObject('Sketch').addConstraint(Sketcher.Constraint('Block',42))
# Gui.Selection.clearSelection()
# Gui.Selection.addSelection('Unnamed','Body','Sketch.Edge32',-14.1767,42.7436,0)
App.getDocument('Unnamed').getObject('Sketch').addConstraint(Sketcher.Constraint('Block',31))
# Gui.Selection.clearSelection()
# Gui.runCommand('Std_Undo',0)
# Gui.Selection.addSelection('Unnamed','Body','Sketch.Edge34',-48.8001,73.053,0)
App.getDocument('Unnamed').getObject('Sketch').addConstraint(Sketcher.Constraint('Block',33))
# Gui.Selection.clearSelection()
# Gui.runCommand('Std_Undo',0)
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
# Gui.Selection.clearSelection()
### Begin command Std_Delete
App.getDocument('Unnamed').getObject('Sketch').delConstraint(175)
App.getDocument('Unnamed').getObject('Sketch').delConstraint(174)
App.getDocument('Unnamed').getObject('Sketch').delConstraint(173)
App.getDocument('Unnamed').getObject('Sketch').delConstraint(172)
App.getDocument('Unnamed').getObject('Sketch').delConstraint(171)
App.getDocument('Unnamed').getObject('Sketch').delConstraint(170)
App.getDocument('Unnamed').getObject('Sketch').delConstraint(169)
App.getDocument('Unnamed').getObject('Sketch').delConstraint(168)
App.getDocument('Unnamed').getObject('Sketch').delConstraint(167)
App.getDocument('Unnamed').getObject('Sketch').delConstraint(166)
App.getDocument('Unnamed').recompute()
### End command Std_Delete
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Gui.Selection.clearSelection()
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.AttachmentSupport if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Unnamed').getObject('Sketch').movePoint(47,0,App.Vector(-8.991141,42.506233,0),0)
# Gui.Selection.clearSelection()
# Gui.Selection.clearSelection()
# Gui.Selection.clearSelection()
# Gui.Selection.clearSelection()
# Gui.runCommand('Std_Undo',0)
# Gui.runCommand('Std_Undo',0)
# Gui.Selection.clearSelection()
# Gui.Selection.clearSelection()
# Gui.Selection.clearSelection()
# Gui.Selection.clearSelection()
# Gui.Selection.clearSelection()
# Gui.Selection.clearSelection()
# Gui.Selection.clearSelection()
### Begin command Std_Delete
App.getDocument('Unnamed').getObject('Sketch').delConstraint(175)
App.getDocument('Unnamed').getObject('Sketch').delConstraint(174)
App.getDocument('Unnamed').getObject('Sketch').delConstraint(173)
App.getDocument('Unnamed').getObject('Sketch').delConstraint(172)
App.getDocument('Unnamed').getObject('Sketch').delConstraint(171)
App.getDocument('Unnamed').getObject('Sketch').delConstraint(170)
App.getDocument('Unnamed').getObject('Sketch').delConstraint(169)
App.getDocument('Unnamed').getObject('Sketch').delConstraint(168)
App.getDocument('Unnamed').getObject('Sketch').delConstraint(167)
App.getDocument('Unnamed').recompute()
### End command Std_Delete
# Gui.Selection.clearSelection()
App.getDocument('Unnamed').getObject('Sketch').movePoint(39,0,App.Vector(-16.613283,42.729572,0),0)
App.getDocument('Unnamed').getObject('Sketch').movePoint(39,3,App.Vector(-16.920233,42.767944,0),0)
# Gui.Selection.addSelection('Unnamed','Body','Sketch.Edge36',-17,43.9957,0.008,False)
### Begin command Std_Delete
App.getDocument('Unnamed').getObject('Sketch').delGeometries([35])
App.getDocument('Unnamed').recompute()
### End command Std_Delete
# Gui.Selection.clearSelection()
# Gui.Selection.addSelection('Unnamed','Body','Sketch.Edge36',-22.9372,37,0.008,False)
### Begin command Std_Delete
App.getDocument('Unnamed').getObject('Sketch').delGeometries([35])
App.getDocument('Unnamed').recompute()
### End command Std_Delete
# Gui.Selection.clearSelection()
# Gui.runCommand('Std_Undo',0)
# Gui.runCommand('Std_Undo',0)
# Gui.runCommand('Sketcher_ConstrainBlock',0)
# Gui.Selection.addSelection('Unnamed','Body','Sketch.Edge36',-17,41.5236,0)
App.getDocument('Unnamed').getObject('Sketch').addConstraint(Sketcher.Constraint('Block',35))
# Gui.Selection.clearSelection()
# Gui.getDocument('Unnamed').resetEdit()
App.ActiveDocument.recompute()
# ActiveSketch = App.getDocument('Unnamed').getObject('Sketch')
# tv = ActiveSketch.ViewObject.TempoVis
# if tv:
#   tv.restore()
# ActiveSketch.ViewObject.TempoVis = None
# del(tv)
# del(ActiveSketch)
# 
# Gui.Selection.addSelection('Unnamed','Body','Sketch.')
App.getDocument('Unnamed').recompute()
# Macro End: /Users/anish/ProBUILD_FreeCAD/Week2Sketch2.FCMacro +++++++++++++++++++++++++++++++++++++++++++++++++
